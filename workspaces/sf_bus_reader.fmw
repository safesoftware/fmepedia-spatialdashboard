FME workspace sf_bus_reader.fmw

Parameters:
- SourceDataset_XML = http://webservices.nextbus.com/service/publicXMLFeed?command=vehicleLocations&a=sf-muni&r=N&t=0   # Source XML File(s)

Readers:
- XML_1: XML from $(SourceDataset_XML)

vehicle (reader XML_1)
    attributes: vehicle.dirTag xml_char(7), vehicle.heading xml_decimal(4,0), vehicle.id xml_decimal(5,0), vehicle.lat xml_decimal(10,7), vehicle.leadingVehicleId xml_decimal(5,0), vehicle.lon xml_decimal(10,5), vehicle.predictable xml_char(6), vehicle.routeTag xml_char(2), vehicle.secsSinceReport xml_decimal(3,0), vehicle.speedKmHr xml_decimal(18,15), xml_fragment xml_xml, xml_id xml_char(16), xml_matched_element xml_char(8)
    -> StringConcatenator
StringConcatenator
    PARM_LINE:
      {
      	"bus_id": "@Value(vehicle.id)",
      	"latitude": "@Value(vehicle.lat)",
      	"longitude": "@Value(vehicle.lon)",
      	"speed": "@Value(vehicle.speedKmHr)"
      }
    VAL_ATTR = notify_content
    -> PythonCaller
Note: Send messages to web sockets
PythonCaller
    PYTHONSYMBOL = FeatureProcessor
    PYTHONSOURCE:
      from websocket import create_connection
      from datetime import datetime
      import time
      import fmeobjects

      # initialize connection
      ws = create_connection("ws://localhost:9998/bus")
      ws.send("provider")

      # Template Function interface:
      def processFeature(feature):
         pass

      # Template Class Interface:
      class FeatureProcessor(object):

         def __init__(self):
             pass

         def input(self,feature):
             global ws

             notifyContent = feature.getAttribute("notify_content")
             ws.send(notifyContent)
             self.pyoutput(feature)

         def close(self):
             ws.close()
             pass
