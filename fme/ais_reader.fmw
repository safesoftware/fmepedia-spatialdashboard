FME workspace ais_reader.fmw

Note: Read the AIS messages
PythonCreator
    NEW_ATTRIBUTES = message
    PYTHONSYMBOL = FeatureCreator
    PYTHONSOURCE:
      import fmeobjects, httplib, os
      # Template Class
      class FeatureCreator(object):
          def __init__(self):
              pass
          def close(self):

              # Create the connection to the stream
              h1 = httplib.HTTPConnection('207.7.148.216',9009)
              h1.request('GET','/')
              resp = h1.getresponse()

              # Read from stream forever
              buffer = ''
              while 1 == 1:
                  buffer += resp.read(100)
                  start = buffer.find('!')
                  end = 0
                  # find each message in the buffer
                  while start > -1 and end > -1:
                      end = buffer.find('!',start+1)
                      if end > -1:
                          mess = buffer[start:end]
                          #print 'message: ' + mess

                          # push out the messages
                          feature = fmeobjects.FMEFeature()
                          feature.setAttribute('message',mess)
                          self.pyoutput(feature)

                          mess = ''
                          buffer = buffer[end:]
                      start = buffer.find('!')
    -> UUIDGenerator
UUIDGenerator
    UUID_ATTR = _uuid
    -> AttributeCreator
AttributeCreator
    ATTR_LIST = file_path,$(FME_MF_DIR_ENCODED)ais_@Value(_uuid).txt
    -> AttributeFileWriter
AttributeFileWriter
    FILE_NAME = @Value(file_path)
    SOURCE_ATTR = message
    CHAR_ENCODING = fme-system
    -> FeatureReader
FeatureReader
    FORMAT = AIS
    FEATURETYPES = ais_addressed_safety_related_message ais_aid_to_navigation_report ais_area_notice ais_assignment_mode_command ais_base_station_report ais_berthing_data ais_binary_acknowledge ais_binary_message_unknown ais_channel_management ais_clearance_time_to_enter_port ais_dangerous_cargo_indication ais_data_link_management_message ais_dgnss_broadcast_binary_message ais_environmental_report ais_extended_class_b_cs_position_report ais_extended_ship_static_voyage_imo236 ais_extended_ship_static_voyage_imo289 ais_fairway_closed ais_group_channel_command ais_interrogation ais_long_range_Broadcast_message ais_marine_traffic_signal ais_meteorological_hydrological_data ais_multiple_slot_binary_message ais_number_persons_on_board ais_position_report ais_route_information ais_safety_related_broadcast_message ais_sar_aircraft_position_report ais_ship_static_and_voyage_related_data ais_single_slot_binary_message ais_standard_class_b_cs_position_report ais_static_data_report ais_synthetic_target ais_text_description ais_tidal_window ais_utc_date_inquiry ais_weather_observation_from_ship_non_wmo ais_weather_observation_from_ship_wmo
    DATASET = @Value(file_path)
    COMBINE_GEOM = Result Geometry Only
    ATTRIBUTES =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
    SUPPORTED_SPATIAL_INTERACTIONS = ENVELOPE_INTERSECT%INTERSECTS%CONTAINS%CROSSES%DISJOINT%EQUALS%OVERLAPS%TOUCHES%WITHIN
    COMBINE_ATTRS = Result Attributes Only
    ais_route_information -> Logger_27
    ais_single_slot_binary_message -> Logger_31
    ais_standard_class_b_cs_position_report -> Logger_32
    ais_static_data_report -> Logger_33
    ais_synthetic_target -> Logger_34
    ais_text_description -> Logger_35
    ais_tidal_window -> Logger_36
    ais_utc_date_inquiry -> Logger_37
    ais_weather_observation_from_ship_non_wmo -> Logger_38
    ais_weather_observation_from_ship_wmo -> Logger_39
    <OTHER> -> Logger_40
    ais_addressed_safety_related_message -> Logger
    ais_aid_to_navigation_report -> Logger_2
    ais_area_notice -> Logger_3
    ais_assignment_mode_command -> Logger_4
    ais_base_station_report -> Logger_5
    ais_berthing_data -> Logger_6
    ais_binary_acknowledge -> Logger_7
    ais_binary_message_unknown -> Logger_8
    ais_channel_management -> Logger_9
    ais_clearance_time_to_enter_port -> Logger_10
    ais_dangerous_cargo_indication -> Logger_11
    ais_data_link_management_message -> Logger_12
    ais_dgnss_broadcast_binary_message -> Logger_13
    ais_environmental_report -> Logger_14
    ais_extended_class_b_cs_position_report -> Logger_15
    ais_extended_ship_static_voyage_imo236 -> Logger_16
    ais_extended_ship_static_voyage_imo289 -> Logger_17
    ais_fairway_closed -> Logger_18
    ais_group_channel_command -> Logger_19
    ais_interrogation -> Logger_20
    ais_long_range_Broadcast_message -> Logger_21
    ais_marine_traffic_signal -> Logger_22
    ais_meteorological_hydrological_data -> Logger_23
    ais_multiple_slot_binary_message -> Logger_24
    ais_number_persons_on_board -> Logger_25
    ais_safety_related_broadcast_message -> Logger_28
    ais_sar_aircraft_position_report -> Logger_29
    ais_ship_static_and_voyage_related_data -> Logger_30
    ais_position_report -> CoordinateExtractor
    INITIATOR -> VariableRetriever
Logger [off]
    MESSAGE = Feature is:
    MAXFEATS = 20
    MAXCOORDS = 20
Logger_2 [off]
    MESSAGE = Feature is:
    MAXFEATS = 20
    MAXCOORDS = 20
Logger_3 [off]
    MESSAGE = Feature is:
    MAXFEATS = 20
    MAXCOORDS = 20
CoordinateExtractor
    Z_DEFAULT = -9999
    IND = 0
    Y_ATTR = _y
    X_ATTR = _x
    Z_ATTR = _z
    -> SQLExecutor
Note: Get ship details
SQLExecutor
    FORMAT = SQLITE3
    COMBINE_ATTRS = Keep Result Attributes if Conflict
    DATASET = D:\userdata\akoning\ais\data\ships.db
    SQL_STATEMENT = SELECT * FROM ship_details WHERE  mmsi_number = "@Value(ais_data_mmsi)"
    EXPOSED_ATTRIBUTE_LIST = call_sign,class_general,class_special,mmsi_number,ship_length,tonnage,vessel_name,class_general_desc,class_individual_desc
    COMBINE_GEOM = Initiator Geometry Only
    RESULT -> StringConcatenator_2
StringConcatenator_2
    PARM_LINE:
      fme_basicstring:19%21%16%29%17%10%18%10%18%17%22%21%22%21%20%19%16%15%20%19%27%26%27%29%3:{
      	"mmsi_number": "@Value(ais_data_mmsi)",
      	"heading": "@Value(ais_data_true_heading)",
      	"latitude": "@Value(_y)",
      	"longitude": "@Value(_x)",
      	"call_sign": "@Value(call_sign)",
      	"class_general": "@Value(class_general)",
      	"class_special": "@Value(class_special)",
      	"ship_length": "@Value(ship_length)",
      	"tonnage": "@Value(tonnage)",
      	"vessel_name": "@Value(vessel_name)",
      	"class_general_desc": "@Value(class_general_desc)",
      	"class_special_desc": "@Value(class_individual_desc)"
      }
    VAL_ATTR = notify_content
    -> PythonCaller
Note: Send messages to web sockets
PythonCaller
    PYTHONSYMBOL = FeatureProcessor
    PYTHONSOURCE:
      from websocket import create_connection
      from datetime import datetime
      import time
      import fmeobjects

      # initialize connection
      ws = create_connection("ws://localhost:9998/ais")
      ws.send("provider")

      # Template Function interface:
      def processFeature(feature):
         pass

      # Template Class Interface:
      class FeatureProcessor(object):

         def __init__(self):
             pass

         def input(self,feature):
             global ws

             notifyContent = feature.getAttribute("notify_content")
             ws.send(notifyContent)
             self.pyoutput(feature)

         def close(self):
             ws.close()
             pass
    -> Logger_26
Logger_26 [off]
    MESSAGE = Feature is:
    MAXFEATS = 20
    MAXCOORDS = 20
Logger_4 [off]
    MESSAGE = Feature is:
    MAXFEATS = 20
    MAXCOORDS = 20
Logger_5 [off]
    MESSAGE = Feature is:
    MAXFEATS = 20
    MAXCOORDS = 20
Logger_6 [off]
    MESSAGE = Feature is:
    MAXFEATS = 20
    MAXCOORDS = 20
Logger_7 [off]
    MESSAGE = Feature is:
    MAXFEATS = 20
    MAXCOORDS = 20
Logger_8 [off]
    MESSAGE = Feature is:
    MAXFEATS = 20
    MAXCOORDS = 20
Logger_9 [off]
    MESSAGE = Feature is:
    MAXFEATS = 20
    MAXCOORDS = 20
Logger_10 [off]
    MESSAGE = Feature is:
    MAXFEATS = 20
    MAXCOORDS = 20
Logger_11 [off]
    MESSAGE = Feature is:
    MAXFEATS = 20
    MAXCOORDS = 20
Logger_12 [off]
    MESSAGE = Feature is:
    MAXFEATS = 20
    MAXCOORDS = 20
Logger_13 [off]
    MESSAGE = Feature is:
    MAXFEATS = 20
    MAXCOORDS = 20
Logger_14 [off]
    MESSAGE = Feature is:
    MAXFEATS = 20
    MAXCOORDS = 20
Logger_15 [off]
    MESSAGE = Feature is:
    MAXFEATS = 20
    MAXCOORDS = 20
Logger_16 [off]
    MESSAGE = Feature is:
    MAXFEATS = 20
    MAXCOORDS = 20
Logger_17 [off]
    MESSAGE = Feature is:
    MAXFEATS = 20
    MAXCOORDS = 20
Logger_18 [off]
    MESSAGE = Feature is:
    MAXFEATS = 20
    MAXCOORDS = 20
Logger_19 [off]
    MESSAGE = Feature is:
    MAXFEATS = 20
    MAXCOORDS = 20
Logger_20 [off]
    MESSAGE = Feature is:
    MAXFEATS = 20
    MAXCOORDS = 20
Logger_21 [off]
    MESSAGE = Feature is:
    MAXFEATS = 20
    MAXCOORDS = 20
Logger_22 [off]
    MESSAGE = Feature is:
    MAXFEATS = 20
    MAXCOORDS = 20
Logger_23 [off]
    MESSAGE = Feature is:
    MAXFEATS = 20
    MAXCOORDS = 20
Logger_24 [off]
    MESSAGE = Feature is:
    MAXFEATS = 20
    MAXCOORDS = 20
Logger_25 [off]
    MESSAGE = Feature is:
    MAXFEATS = 20
    MAXCOORDS = 20
Logger_27 [off]
    MESSAGE = Feature is:
    MAXFEATS = 20
    MAXCOORDS = 20
Logger_28 [off]
    MESSAGE = Feature is:
    MAXFEATS = 20
    MAXCOORDS = 20
Logger_29 [off]
    MESSAGE = Feature is:
    MAXFEATS = 20
    MAXCOORDS = 20
Logger_30 [off]
    MESSAGE = Feature is:
    MAXFEATS = 20
    MAXCOORDS = 20
Logger_31 [off]
    MESSAGE = Feature is:
    MAXFEATS = 20
    MAXCOORDS = 20
Logger_32 [off]
    MESSAGE = Feature is:
    MAXFEATS = 20
    MAXCOORDS = 20
Logger_33 [off]
    MESSAGE = Feature is:
    MAXFEATS = 20
    MAXCOORDS = 20
Logger_34 [off]
    MESSAGE = Feature is:
    MAXFEATS = 20
    MAXCOORDS = 20
Logger_35 [off]
    MESSAGE = Feature is:
    MAXFEATS = 20
    MAXCOORDS = 20
Logger_36 [off]
    MESSAGE = Feature is:
    MAXFEATS = 20
    MAXCOORDS = 20
Logger_37 [off]
    MESSAGE = Feature is:
    MAXFEATS = 20
    MAXCOORDS = 20
Logger_38 [off]
    MESSAGE = Feature is:
    MAXFEATS = 20
    MAXCOORDS = 20
Logger_39 [off]
    MESSAGE = Feature is:
    MAXFEATS = 20
    MAXCOORDS = 20
Logger_40 [off]
    MESSAGE = Feature is:
    MAXFEATS = 20
    MAXCOORDS = 20
VariableRetriever
    SCOPE = Global
    VALUE_ATTR = file_path_del
    VARNAME = file_path
    -> Tester
Tester
    TEST_DESCRIPTION = ""
    TEST_CLAUSE = TEST "file_path_del" NOT_ATTRIBUTE_IS_EMPTY "<Unused>"
    BOOL_OP = OR
    TEST_MODE = Automatic
    PASSED -> PythonCaller_2
    FAILED -> VariableSetter
PythonCaller_2
    PYTHONSYMBOL = FeatureProcessor
    PYTHONSOURCE:
      import fmeobjects, os, time
      # Template Function interface:
      def processFeature(feature):
         pass

      # Template Class Interface:
      class FeatureProcessor(object):

         def __init__(self):
             pass

         def input(self,feature):

             file_path = feature.getAttribute('file_path_del')

             os.remove(file_path)

             self.pyoutput(feature)

         def close(self):
             pass
    -> VariableSetter
VariableSetter
    VALUE = @Value(file_path)
    SCOPE = Global
    VARNAME = file_path
