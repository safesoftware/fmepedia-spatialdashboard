FME workspace ufo.fmw

Creator
    GEOMTYPE = Geometry Object
    GEOM = <?xml version="1.0" encoding="US_ASCII" standalone="no" ?><geometry><point><coord x="-123" y="38"/></point></geometry>
    NUM = 400
    CREATED -> Offsetter
Note: Create movement
Offsetter
    YOFF = @Value(_creation_instance)*-0.00125
    ZOFF = 0
    XOFF = @Value(_creation_instance)*.005
    OFFSET -> ExpressionEvaluator_2
ExpressionEvaluator_2
    EXPRESSION = (@Value(_creation_instance)%8)+1
    VAL_ATTR = icon_position
    -> AttributeCreator
AttributeCreator
    ATTR_LIST = title,FMEROX,icon_url,https://dl.dropbox.com/u/3725882/ufo/ufo_@Value(icon_position).gif,icon_size,50
    -> CoordinateExtractor
CoordinateExtractor
    Z_DEFAULT = -9999
    IND = 0
    Y_ATTR = latitude
    X_ATTR = longitude
    Z_ATTR = _z
    -> StringConcatenator
Note: Create json payload
StringConcatenator
    PARM_LINE:
      {
      	"id": "10000001",
      	"latitude": "@Value(latitude)",
      	"longitude": "@Value(longitude)",
      	"title": "@Value(title)",
      	"icon_url": "@Value(icon_url)",
      	"icon_size": "@Value(icon_size)"
      }
    VAL_ATTR = notify_content
    -> Decelerator
Note: Rate of movement
Decelerator
    DECEL_TYPE = Per Feature Delay
    DELAY = .1
    -> PythonCaller
Note: Send messages to web sockets
PythonCaller
    PYTHONSYMBOL = FeatureProcessor
    PYTHONSOURCE:
      from websocket import create_connection
      from datetime import datetime
      import time
      import fmeobjects

      # initialize connection
      ws = create_connection("ws://localhost:9998/custom")
      ws.send("provider")

      # Template Function interface:
      def processFeature(feature):
         pass

      # Template Class Interface:
      class FeatureProcessor(object):

         def __init__(self):
             pass

         def input(self,feature):
             global ws

             notifyContent = feature.getAttribute("notify_content")
             ws.send(notifyContent)
             self.pyoutput(feature)

         def close(self):
             ws.close()
             pass
