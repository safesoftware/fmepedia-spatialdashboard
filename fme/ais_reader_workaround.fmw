FME workspace ais_reader_workaround.fmw

Parameters:
- prev_path =   # Previous file path for deletion
- SourceDataset_AIS = $(FME_SHAREDRESOURCE_DATA)/Demos/2012-07-02_SanFran_AIS_recording.txt   # Source AIS File
- sqlite_file = $(FME_SHAREDRESOURCE_DATA)/Demos/ships.db

Readers:
- AIS_1: AIS from $(SourceDataset_AIS)

ais_position_report (reader AIS_1)
    attributes: ais_header_prefix buffer, ais_header_message_type char(6), ais_header_message_id char(2), ais_header_channel char(1), ais_header_time_stamp uint32, ais_header_destination_id buffer, ais_header_source_id buffer, ais_header_comment buffer, ais_header_counter uint16, ais_header_group_code buffer, ais_data_message_type uint8, ais_data_repeat_indicator uint8, ais_data_mmsi uint32, ais_data_navigation_status uint8, ais_data_rate_of_turn int16, ais_data_speed_over_ground real32, ais_data_position_accuracy uint8, ais_data_course_over_ground real32, ais_data_true_heading uint16, ais_data_time_stamp uint8, ais_data_maneuver_indicator uint8, ais_data_raim_flag uint8, ais_data_radio_status uint32
    -> Decelerator
Decelerator
    DECEL_TYPE = Per Feature Delay
    DELAY = 0.1
    -> CoordinateExtractor
WebSocketSender
    PREAMBLE:
      {
          "ws_op" : "open",
          "ws_stream_id" : "ship_in"
      }
    DATA = @Value(notify_content)
    HOST = wss://localhost:7078/websocket
    -> AttributeRemover

Bookmark: Create location message with ship details
CoordinateExtractor
    Y_ATTR = _y
    X_ATTR = _x
    Z_DEFAULT = -9999
    Z_ATTR = _z
    IND = 0
    -> SQLExecutor
Note: Get ship details
SQLExecutor
    SQL_STATEMENT = SELECT * FROM ship_details WHERE  mmsi_number = "@Value(ais_data_mmsi)"
    EXPOSED_ATTRIBUTE_LIST = call_sign,class_general,class_special,mmsi_number,ship_length,tonnage,vessel_name,class_general_desc,class_individual_desc
    DATASET = $(sqlite_file)
    COMBINE_GEOM = Initiator Geometry Only
    COMBINE_ATTRS = Keep Result Attributes if Conflict
    FORMAT = SQLITE3
    RESULT -> StringConcatenator_3
StringConcatenator_3
    PARM_LINE:
      {
          ws_op : "send",
          ws_msg : '{"mmsi_number": "@Value(ais_data_mmsi)",	"heading": "@Value(ais_data_true_heading)","latitude": "@Value(_y)","longitude": "@Value(_x)","call_sign": "@Value(call_sign)","class_general": "@Value(class_general)","class_special": "@Value(class_special)","ship_length": "@Value(ship_length)","tonnage": "@Value(tonnage)","vessel_name": "@Value(vessel_name)",	"class_general_desc": "@Value(class_general_desc)",	"class_special_desc": "@Value(class_individual_desc)"}'
      }
    VAL_ATTR = notify_content
    -> WebSocketSender

Bookmark: Submit the next AIS job
AttributeRemover
    REMOVE_ATTRS = ais_data_mmsi,ais_data_course_over_ground,ais_data_rate_of_turn,ais_data_repeat_indicator,ais_header_message_id,ais_data_radio_status,ais_data_message_type,ais_header_channel,ais_header_prefix,ais_header_message_type,ais_data_navigation_status,ais_data_true_heading,ais_data_position_accuracy,ais_data_time_stamp,ais_data_speed_over_ground,ais_data_raim_flag,ais_data_maneuver_indicator,_x,_y,_z,call_sign,class_general,class_special,mmsi_number,ship_length,tonnage,vessel_name,class_general_desc,class_individual_desc,notify_content
    -> GeometryRemover
GeometryRemover
    -> Aggregator
Aggregator
    SEP = ,
    CONTAIN_INDIVID_GEOMS = No
    ACCUM_ATTRS_NAME = No
    ORDERED = No
    AGGREGATE -> VariableRetriever
VariableRetriever
    SCOPE = Global
    VARNAME = filename_del
    VALUE_ATTR = filename_del
    -> FMEServerJobSubmitter
FMEServerJobSubmitter
    PASSWORD =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
    USERNAME = fmepediademos
    SERVER_NAME = http://fmepedia2014-safe-software.fmecloud.com
    WORKSPACE_NAME = ais_reader_workaround.fmw
    BLOCKING = No
    REPOSITORY = spatialdashboard
    SERVER_PORT = 0
    WORKSPACE_PARAMETERS = prev_path,,SourceDataset_AIS,$(SourceDataset_AIS),sqlite_file,$(sqlite_file)
    SUBSECTION = SERVER_JOB_SUBMITTER
    PRIORITY = 1
    SUCCEEDED -> Logger_26
Logger_26
    MESSAGE = Feature is:
    MAXFEATS = 20
    MAXCOORDS = 20
