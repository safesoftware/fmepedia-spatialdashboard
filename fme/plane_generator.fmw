FME workspace plane_generator.fmw

Parameters:
- min_y = 615000   # Minimum y value
- max_y = 660000   # Maximum y value
- min_x = 1790000   # Minimum x value
- max_x = 1900000   # Maximum x value
- num_planes = 30   # Number of planes
- DestDataset_FFS = $(FME_SHAREDRESOURCE_TEMP)/planez.ffs   # Destination FME Feature Store (FFS) File

Writers:
- FFS_1: FFS to $(DestDataset_FFS)

Hangar: Creator
    COORDSYS = CA83-III
    NUM = $(num_planes)
    GEOMTYPE = Geometry Object
    CREATED -> AttributeCreator
AttributeCreator
    ATTR_LIST = _iterations,0
    -> FlightAndAircraftGenerator
FlightAndAircraftGenerator: PythonCaller
    PYTHONSOURCE:
      import fmeobjects, string, random
      # Template Function interface:
      def processFeature(feature):

          #Create flight number
          flight = []
          for x in range (2):
              flight.append(random.choice(string.ascii_uppercase))
          flight.append(str(random.randrange(1000)))
          code = "".join(flight)
          feature.setAttribute("flight_id", code)

          #Choose plane model
          model = random.choice([
              "Boeing 737",
              "Boeing 777",
              "Cessna 206",
              "Airbus A320",
              "Antonov An-2",
              "de Havilland Mosquito",
              "Airbus A380",
              "Douglas DC-8",
              "McDonnell Douglas DC-10",
              "Douglas DC-9"
          ])
          feature.setAttribute("aircraft_model", model)

          return feature
    PYTHONSYMBOL = processFeature
    NEW_ATTRIBUTES = flight_id aircraft_model
    -> DuplicatePlaneRemover
DuplicatePlaneRemover: DuplicateRemover
    KEYATTR = flight_id
    UNIQUE -> XCoordGenerator
XCoordGenerator: RandomNumberGenerator
    RESULT_ATTR = x_coord
    MAX = $(max_x)
    PLACES = 3
    MIN = $(min_x)
    -> YCoordGenerator
YCoordGenerator: RandomNumberGenerator
    RESULT_ATTR = y_coord
    MAX = $(max_y)
    PLACES = 3
    MIN = $(min_y)
    -> HeadingGenerator
HeadingGenerator: RandomNumberGenerator
    RESULT_ATTR = heading
    MAX = 360
    PLACES = 0
    MIN = 0
    -> SpeedGenerator
SpeedGenerator: RandomNumberGenerator
    RESULT_ATTR = speed
    MAX = 800
    PLACES = 0
    MIN = 300
    -> SpeedProcessor
SpeedProcessor: AttributeCreator
    ATTR_LIST = speed,@int(@Value(speed))
    -> AltitudeGenerator
AltitudeGenerator: RandomNumberGenerator
    RESULT_ATTR = altitude
    MAX = 12000
    PLACES = 0
    MIN = 7000
    -> 2DPointReplacer
2DPointReplacer
    XVALATTR = @Value(x_coord)
    YVALATTR = @Value(y_coord)
    POINT -> Planes (writer FFS_1)
Planes (writer FFS_1)
