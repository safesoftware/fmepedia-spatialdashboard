FME workspace sd_bus.fmw

Parameters:
- SourceDataset_XML = http://webservices.nextbus.com/service/publicXMLFeed?command=vehicleLocations&a=sf-muni&r=N&t=0   # gui_Source XML File(s):_5190

Readers:
- XML_1: XML from $(SourceDataset_XML)

Note: sd_bus.fmw / This workspace reads XML data from a feed and sends out a WebSocket message for each bus in the response. It should be run on a schedule. Please be mindful of the polling frequency, as this is a freely provided service that should not be abused.
vehicle (reader XML_1)
    attributes: vehicle xml_char(1), vehicle.dirTag xml_char(7), vehicle.heading xml_decimal(4,0), vehicle.id xml_decimal(5,0), vehicle.lat xml_decimal(10,7), vehicle.leadingVehicleId xml_decimal(5,0), vehicle.lon xml_decimal(10,5), vehicle.predictable xml_char(6), vehicle.routeTag xml_char(2), vehicle.secsSinceReport xml_decimal(3,0), vehicle.speedKmHr xml_decimal(3,0), xml_fragment xml_xml, xml_id xml_char(16), xml_matched_element xml_char(8), xml_parent_child_pos xml_char(1), xml_parent_id xml_char(1)
    -> JSONTemplater
JSONTemplater
    RESULT_ATTRIBUTE = ws_msg
    VISIBLE_QUERY_VALIDATE = Yes
    ROOT_QUERY_EXPR:
      {
          "bus_id": fme:get-attribute("vehicle.id"),
          "latitude": fme:get-attribute("vehicle.lat"),
          "longitude": fme:get-attribute("vehicle.lon"),
          "speed": fme:get-attribute("vehicle.speedKmHr")
      }
    -> WebSocketSender
Note: WebSocketSender [WebSocketSender] / WebSocket Server URL: wss://localhost:7078/websocket / Connection Preamble: { / ws_op : 'open', / ws_stream_id : 'sd_bus' / } / Data to Transmit: { / ws_op: 'send', / ws_msg: '@Value(ws_msg)' / } / Verify SSL Certificates: Yes
WebSocketSender
    PREAMBLE:
      {
          ws_op : 'open',
          ws_stream_id : 'sd_bus'
      }
    DATA:
      {
          ws_op: 'send',
          ws_msg: '@Value(ws_msg)'
      }
    VERIFY_SSL_CERTIFICATES = Yes
    HOST = wss://localhost:7078/websocket

FME custom transformer Geohash_2
This transformer will calculate a list of Geohash polygons ("http://en.wikipedia.org/wiki/Geohash") that will approximate the shape of the input polygon. 
The maximum length of the Geohashes ( and thus the resolution) can be set by the user.
The Geohash list is pipe ("|") separated and stored in the attribute "_geohash".
Copyright (c) 2013 Safe Software Inc.
Permission is granted to anyone, free of charge, to use, modify and distribute the object code form of this tranformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- HASH =   # Maximum Hash Length

BASE (input)
    -> AttributeExposer
Note: Expose input attributes
AttributeExposer
    ATTR_LIST = _id
    -> SpatialFilter [input 1]
    -> SpatialFilter_2 [input 1]
TILES (input)
    -> AttributeExposer_2
Note: Expose input attributes
AttributeExposer_2
    ATTR_LIST = _id,_geometry
    -> StringLengthCalculator
Note: Calculate geohash length
StringLengthCalculator
    SRC_ATTR = _geometry
    LENGTH_ATTR = _length
    -> Tester
Note: If geohash length / meets target, bail out
Tester
    TEST_MODE = Automatic
    BOOL_OP = OR
    TEST_CLAUSE = TEST @Value(_length) < $(HASH)
    TEST_DESCRIPTION = ""
    PASSED -> Cloner
    FAILED -> Cloner_2
Note: Create 32 copies of geohash
Cloner
    COPIES = 32
    COPYATT = _copynum
    COPY -> AttributeValueMapper
Note: Convert copy / number to base32
AttributeValueMapper
    SRC = _copynum
    DIRECTION = Forward (Source To Destination)
    DEFAULT_VALUE = KEY
    LUT = 10,b,11,c,12,d,13,e,14,f,15,g,16,h,17,j,18,k,19,m,20,n,21,p,22,q,23,r,24,s,25,t,26,u,27,v,28,w,29,x,30,y,31,z
    VAL_ATTR = _looked_up
    -> StringConcatenator
Note: Add converted copy / number to geohash
StringConcatenator
    PARM_LINE = @Value(_geometry)@Value(_looked_up)
    VAL_ATTR = _geometry
    -> GeometryReplacer
Note: Replace old geometry / from new geohash
GeometryReplacer
    KIND_LONG = Geohash
    OUTPUT_POINT_DISPLAY = Area
    ATTR = _geometry
    -> SpatialFilter [input 2]
Note: Extract all new polygons / completely within source
SpatialFilter
    BASE_TYPE = Multiple Bases
    GROUP_BY = _id
    PASS_CRITERIA = Pass Against One Base
    MERGE_ATTRS = No
    CURVE_BOUNDARY_RULE_PARAM = Default Rule
    PREDICATES = CONTAINS
    USE_BOUNDING_BOX = No
    FAILED -> SpatialFilter_2 [input 2]
    PASSED -> AttributeRemover
Note: Clean up attributes
AttributeRemover
    REMOVE_ATTRS = _length,_looked_up
    -> INSIDE (output)
INSIDE (output)
Note: Extract all polygons / intersecting edge
SpatialFilter_2
    BASE_TYPE = Multiple Bases
    GROUP_BY = _id
    PASS_CRITERIA = Pass Against One Base
    MERGE_ATTRS = No
    CURVE_BOUNDARY_RULE_PARAM = Default Rule
    PREDICATES = INTERSECTS
    USE_BOUNDING_BOX = No
    PASSED -> AttributeRemover_2
Note: Placeholder
Cloner_2
    COPIES = 1
    COPYATT = _copynum
    COPY -> AttributeRemover_2
Note: Clean up attributes
AttributeRemover_2
    REMOVE_ATTRS = _length,_looked_up
    -> EDGE (output)
EDGE (output)

FME custom transformer LoopFilter_3
Tests whether a line is a loop, i.e. whether its end matches the beginning.
The transformers outputs loops through PASSED port, and non-loops through FAILED port.
An isLoop attribute is added to each feature. 1 means the feature is loop, and zero means it is not.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> LineFilter
Note: LoopFilter / Dmitri Bagh / July 11, 2005
LineFilter: GeometryFilter
    LINE -> LoopTester
    POINT -> NON-LINEAR (output)
    ARC -> NON-LINEAR (output)
    AREA -> NON-LINEAR (output)
    ELLIPSE -> NON-LINEAR (output)
    TEXT -> NON-LINEAR (output)
    NULL -> NON-LINEAR (output)
Note: LoopTester [ExpressionEvaluator:1] / _isLoop = (@Coordinate(x,0)-@Coordinate(x,-1))||(@Coordinate(y,0)-@Coordinate(y,-1)) / Version: 1
Note: Evaluates to 0 if feature is loop, and 1, if it is not.
LoopTester: ExpressionEvaluator
    EXPRESSION = (@Coordinate(x,0)-@Coordinate(x,-1))||(@Coordinate(y,0)-@Coordinate(y,-1))
    VAL_ATTR = _isLoop
    -> TESTER
Note: TESTER [Tester:1] / Test Description: <not set> / TEST &_isLoop = 0 / Condition: OR / Composite Test Expression: <not set> / Version: 1
TESTER: Tester
    TEST_MODE = Automatic
    BOOL_OP = OR
    TEST_CLAUSE = TEST &_isLoop = 0
    TEST_LIST = &_isLoop,=,0
    PASSED -> PASSED (output)
    FAILED -> FAILED (output)
PASSED (output)
FAILED (output)
NON-LINEAR (output)

FME custom transformer SOAPSender_2
Submit a SOAP request using HTTP POST to a web service using an XML formatted body and header. The user is required to supply a valid XML fragment containing the body of the SOAP request, and optionally the SOAP header.
Please see http://www.w3.org/TR/soap/ for more information on the SOAP protocol.
Target URL: The URL of the deployed web service that the SOAP request will be sent to.
    SOAP Version: Depending on the web service, only SOAP 1.1 or 1.2 may be supported.
    SOAP Body: A valid SOAP body should be provided here, formatted as XML.
    SOAP Header (Optional): A valid SOAP header should be provided here if desired, formatted as XML. 
    SOAP Action: SOAP requests provide an action field, which describes the intent of the message. If left blank, no intent is provided; otherwise, the string provided will be used as the action. The string "" is often used to use the target URL as the intent string. 
All other options exposed are documented under the HTTPFetcher in the FME Transformers Reference Guide.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
3) Use of GeoNames services is licensed under a Creative Commons Attribution 3.0 License ( http://creativecommons.org/licenses/by/3.0/ )
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- TARGET_URL =   # Target URL
- SOAP_CONTENT_TYPE = text/xml   # SOAP Version
- SOAP_BODY =   # SOAP Body
- SOAP_HEADER =   # SOAP Header
- SOAP_ACTION =   # SOAP Action
- REQUEST_HEADER =   # HTTP Request Headers
- USE_COOKIES = No   # Use Cookies
- AUTH_USERNAME =   # HTTP Authentication Username
- AUTH_PASSWORD =   # HTTP Authentication Password
- AUTH_METHOD = Basic   # HTTP Authentication Method
- PROXY_URL =   # Proxy URL
- PROXY_PORT =   # Proxy Port
- PROXY_USERNAME =   # Proxy Username
- PROXY_PASSWORD =   # Proxy Password
- PROXY_AUTH_METHOD = Basic   # Proxy Authentication Method

INPUT (input)
    -> AttributeCreator
OUTPUT (output)
Cloner_2
    COPIES = 1
    COPY -> AttributeRemover_2
<REJECTED> (output)

Bookmark: Add attributes
Note: Turn parameters / into attributes
AttributeCreator
    ATTR_LIST = _soap_action,$(SOAP_ACTION),_soap_content_type,$(SOAP_CONTENT_TYPE),_soap_body,$(SOAP_BODY),_target_url,$(TARGET_URL)
    -> AttributeCreator_2

Bookmark: Add header
Note: Add SOAP header
AttributeCreator_2
    ATTR_LIST = _soap_header,$(SOAP_HEADER)
    -> AttributeFilter

Bookmark: Decide SOAP version
Note: SOAP v1.1 uses text/xml / SOAP v1.2 uses application/soap+xml
AttributeFilter
    ATTR_VALUES = application/soap+xml,text/xml,<BLANK>,<UNFILTERED>
    ATTR_NAME = _soap_content_type
    application/soap+xml -> Tester_2
    text/xml -> Tester_3
    <BLANK> -> Cloner
    <UNFILTERED> -> Cloner

Bookmark: SOAP Action
Note: Test empty SOAP action
Tester_2
    TEST_MODE = Automatic
    BOOL_OP = OR
    TEST_CLAUSE = TEST "_soap_action" NOT_ATTRIBUTE_IS_EMPTY "<Unused>"
    TEST_DESCRIPTION = Test for empty SOAP action
    FAILED -> AttributeCreator_4
    PASSED -> Tester_4
Note: Special case: empty quotes
Tester_4
    TEST_MODE = Automatic
    BOOL_OP = AND
    TEST_CLAUSE:
      TEST "@Value(_soap_action)" BEGINS_WITH "\""
      TEST "@Value(_soap_action)" ENDS_WITH "\""
    TEST_DESCRIPTION = Check for quotes
    PASSED -> AttributeCreator_3
    FAILED -> AttributeCreator_7
AttributeCreator_3
    ATTR_LIST = _upload_content_type,@Value(_soap_content_type); action=@Value(_soap_action)
    -> XMLTemplater_2
AttributeCreator_7
    ATTR_LIST = _upload_content_type,@Value(_soap_content_type); action="@Value(_soap_action)"
    -> XMLTemplater_2
AttributeCreator_4
    ATTR_LIST = _upload_content_type,@Value(_soap_content_type)
    -> XMLTemplater_2
Tester_3
    TEST_MODE = Automatic
    BOOL_OP = OR
    TEST_CLAUSE = TEST "_soap_action" NOT_ATTRIBUTE_IS_EMPTY "<Unused>"
    TEST_DESCRIPTION = Test for empty SOAP action
    FAILED -> AttributeCreator_6
    PASSED -> Tester_5
Tester_5
    TEST_MODE = Automatic
    BOOL_OP = AND
    TEST_CLAUSE:
      TEST "@Value(_soap_action)" BEGINS_WITH "\""
      TEST "@Value(_soap_action)" ENDS_WITH "\""
    TEST_DESCRIPTION = Check for quotes
    PASSED -> AttributeCreator_5
    FAILED -> AttributeCreator_8
AttributeCreator_5
    ATTR_LIST:
      _request_header,$(REQUEST_HEADER)
      SOAPAction: @Value(_soap_action)
    -> XMLTemplater
AttributeCreator_8
    ATTR_LIST:
      _request_header,$(REQUEST_HEADER)
      SOAPAction: "@Value(_soap_action)"
    -> XMLTemplater
AttributeCreator_6
    ATTR_LIST:
      _request_header,$(REQUEST_HEADER)
      SOAPAction;
    -> XMLTemplater
Cloner
    COPIES = 1
    COPY -> Cloner_2

Bookmark: Create and upload request
XMLTemplater_2
    OUTPUT_XML_HEADER = Yes
    RESULT_ATTRIBUTE = _soap_request
    VISIBLE_QUERY_VALIDATE = Yes
    ROOT_QUERY_EXPR:
      declare namespace xsi="http://www.w3.org/2001/XMLSchema-instance";
      declare namespace xsd="http://www.w3.org/2001/XMLSchema";

      <soap12:Envelope xmlns:soap12="http://www.w3.org/2003/05/soap-envelope/">
      {
      if (fme:has-attribute("_soap_header") and
          not(fme:get-attribute("_soap_header") eq "")) then
          <soap12:Header>{fme:get-xml-attribute("_soap_header")}</soap12:Header>
      else ()
      }
      <soap12:Body>
      {fme:get-xml-attribute("_soap_body")}
      </soap12:Body>
      </soap12:Envelope>
    -> HTTPUploader_2
HTTPUploader_2
    TARGET_ATTR = _soap_response
    AUTH_METHOD = $(AUTH_METHOD)
    UPLOAD_BODY = @Value(_soap_request)
    STATUS_CODE_ATTR = _http_status_code
    UPLOAD_METHOD = POST
    TARGET_URL = @Value(_target_url)
    AUTH_USERNAME = $(AUTH_USERNAME)
    PROXY_PORT = $(PROXY_PORT)
    REQUEST_HEADER = $(REQUEST_HEADER)
    USE_COOKIES = $(USE_COOKIES)
    PROXY_USERNAME = $(PROXY_USERNAME)
    AUTH_PASSWORD = $(AUTH_PASSWORD)
    PROXY_AUTH_METHOD = $(PROXY_AUTH_METHOD)
    PROXY_URL = $(PROXY_URL)
    UPLOAD_CONTENT_TYPE = @Value(_upload_content_type)
    ERROR_ATTR = _http_error
    RESPONSE_HEADER_LIST_ATTR = _http_headers
    PROXY_PASSWORD = $(PROXY_PASSWORD)
    USE_RESPONSE_ENCODING = Yes
    -> XQueryExtractor_3
    <REJECTED> -> Cloner_2
Note: Put together the SOAP / header and body
XMLTemplater
    OUTPUT_XML_HEADER = Yes
    RESULT_ATTRIBUTE = _soap_request
    VISIBLE_QUERY_VALIDATE = Yes
    ROOT_QUERY_EXPR:
      declare namespace xsi="http://www.w3.org/2001/XMLSchema-instance";
      declare namespace xsd="http://www.w3.org/2001/XMLSchema";

      <soap11:Envelope xmlns:soap11="http://schemas.xmlsoap.org/soap/envelope/">
      {
      if (fme:has-attribute("_soap_header") and
          not(fme:get-attribute("_soap_header") eq "")) then
          <soap11:Header>{fme:get-xml-attribute("_soap_header")}</soap11:Header>
      else ()
      }
      <soap11:Body>
      {fme:get-xml-attribute("_soap_body")}
      </soap11:Body>
      </soap11:Envelope>
    -> HTTPUploader
Note: Upload the request
HTTPUploader
    TARGET_ATTR = _soap_response
    AUTH_METHOD = $(AUTH_METHOD)
    UPLOAD_BODY = @Value(_soap_request)
    STATUS_CODE_ATTR = _http_status_code
    UPLOAD_METHOD = POST
    TARGET_URL = @Value(_target_url)
    AUTH_USERNAME = $(AUTH_USERNAME)
    PROXY_PORT = $(PROXY_PORT)
    REQUEST_HEADER = @Value(_request_header)
    USE_COOKIES = $(USE_COOKIES)
    PROXY_USERNAME = $(PROXY_USERNAME)
    AUTH_PASSWORD = $(AUTH_PASSWORD)
    PROXY_AUTH_METHOD = $(PROXY_AUTH_METHOD)
    PROXY_URL = $(PROXY_URL)
    UPLOAD_CONTENT_TYPE = $(SOAP_CONTENT_TYPE)
    ERROR_ATTR = _http_error
    RESPONSE_HEADER_LIST_ATTR = _http_headers
    PROXY_PASSWORD = $(PROXY_PASSWORD)
    USE_RESPONSE_ENCODING = Yes
    -> XQueryExtractor
    <REJECTED> -> Cloner_2

Bookmark: Extract body
Note: Extract the body / from response
XQueryExtractor_3
    XML_ATTR = _soap_response
    SEPARATOR_VALUE = ,
    WRITE_XML_HEADER = No
    XML_TYPE = Attribute specifying XML
    XQUERY_TYPE = XQuery expression
    RESULT_ATTRIBUTE = _unused
    XML_REMOVE_SOURCE_ATTR = No
    RESULT_TYPE_NAME = Separated values
    QUERY_EXPR:
      declare namespace soap12="http://www.w3.org/2003/05/soap-envelope/";
      declare namespace soap11="http://schemas.xmlsoap.org/soap/envelope/";

      fme:set-attribute("_soap_body",//soap12:Body/*)
    QUERY_RESULTS -> XQueryExtractor_4
    INVALID -> AttributeRemover_2
XQueryExtractor
    XML_ATTR = _soap_response
    SEPARATOR_VALUE = ,
    WRITE_XML_HEADER = No
    XML_TYPE = Attribute specifying XML
    XQUERY_TYPE = XQuery expression
    RESULT_ATTRIBUTE = _unused
    XML_REMOVE_SOURCE_ATTR = No
    RESULT_TYPE_NAME = Separated values
    QUERY_EXPR:
      declare namespace soap12="http://www.w3.org/2003/05/soap-envelope/";
      declare namespace soap11="http://schemas.xmlsoap.org/soap/envelope/";

      fme:set-attribute("_soap_body",//soap11:Body/*)
    QUERY_RESULTS -> XQueryExtractor_2
    INVALID -> Cloner_2

Bookmark: Extract header
Note: Extract the header / from response
XQueryExtractor_4
    XML_ATTR = _soap_response
    SEPARATOR_VALUE = ,
    WRITE_XML_HEADER = No
    XML_TYPE = Attribute specifying XML
    XQUERY_TYPE = XQuery expression
    RESULT_ATTRIBUTE = _unused
    XML_REMOVE_SOURCE_ATTR = No
    RESULT_TYPE_NAME = Separated values
    QUERY_EXPR:
      declare namespace soap12="http://www.w3.org/2003/05/soap-envelope/";
      declare namespace soap11="http://schemas.xmlsoap.org/soap/envelope/";

      fme:set-attribute("_soap_header",//soap12:Header/*)
    QUERY_RESULTS -> AttributeRemover
    INVALID -> AttributeRemover_2
XQueryExtractor_2
    XML_ATTR = _soap_response
    SEPARATOR_VALUE = ,
    WRITE_XML_HEADER = No
    XML_TYPE = Attribute specifying XML
    XQUERY_TYPE = XQuery expression
    RESULT_ATTRIBUTE = _unused
    XML_REMOVE_SOURCE_ATTR = No
    RESULT_TYPE_NAME = Separated values
    QUERY_EXPR:
      declare namespace soap12="http://www.w3.org/2003/05/soap-envelope/";
      declare namespace soap11="http://schemas.xmlsoap.org/soap/envelope/";

      fme:set-attribute("_soap_header",//soap11:Header/*)
    QUERY_RESULTS -> AttributeRemover
    INVALID -> AttributeRemover_2

Bookmark: Remove attributes
Note: Remove temporary attributes
AttributeRemover
    LIST_ATTRS = <Unused>{}
    REMOVE_ATTRS = _soap_request,_request_header,_soap_action,_soap_content_type,_target_url,_unused,_upload_content_type
    -> OUTPUT (output)
Note: Remove unneeded attributes
AttributeRemover_2
    LIST_ATTRS = <Unused>{}
    REMOVE_ATTRS = _soap_action,_soap_content_type,_soap_body,_target_url,_soap_header,_request_header,_soap_request,_unused,_upload_content_type
    -> <REJECTED> (output)

FME custom transformer DateDifferenceCalculator_2
Calculates the difference in time between two dates.
Select Start Date Attribute, End Date Attribute and input date format string. See DateFormatter documentation for more detailed explanations of date format strings.
Also select the units you wish the time difference to be expressed in. Time Difference will be stored in _TimeDifference attribute.
Copyright (c) 2013 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- SRC_ATTR =   # " " Start Date
- SRC_ATTR_2 =   # " " End Date
- FMT = %Y%m%d   # Input Date Format
- Unit = 86400   # Output Time Units

INPUT (input)
    -> AttributeCreator
Note: Retrieve parameters
AttributeCreator
    NUM_PRIOR_FEATURES = 0
    ATTR_LIST = DDC_StartDate,@Value($(SRC_ATTR)),DDC_EndDate,@Value($(SRC_ATTR_2))
    NUM_SUBSEQUENT_FEATURES = 0
    -> DateFormatter
Note: Convert temp Date Attributes / to seconds since UNIX Epoch
DateFormatter
    DATE_ATTR = DDC_StartDate,DDC_EndDate
    FMT = %s
    SRCFMT = $(FMT)
    -> ExpressionEvaluator
Note: Subtract Dates and / convert to desired unit
ExpressionEvaluator
    EXPRESSION = @round(1.0*(@Value(DDC_EndDate)-@Value(DDC_StartDate))/$(Unit))
    VAL_ATTR = _TimeDifference
    -> AttributeRemover
Note: Remove temp attributes
AttributeRemover
    REMOVE_ATTRS = DDC_StartDate,DDC_EndDate
    -> OUTPUT (output)
OUTPUT (output)

FME custom transformer LoopFilter_4
Tests whether a line is a loop, i.e. whether its end matches the beginning.
The transformers outputs loops through PASSED port, and non-loops through FAILED port.
The isLoop attribute added to each feature. 1 means the feature is loop, and zero means it is not.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> LineFilter
Note: LoopFilter / Dmitri Bagh / July 11, 2005
LineFilter: GeometryFilter
    LINE -> LoopTester
    POINT -> NON-LINEAR (output)
    ARC -> NON-LINEAR (output)
    AREA -> NON-LINEAR (output)
    ELLIPSE -> NON-LINEAR (output)
    TEXT -> NON-LINEAR (output)
    NULL -> NON-LINEAR (output)
Note: LoopTester [ExpressionEvaluator:1] / _isLoop = (@Coordinate(x,0)-@Coordinate(x,-1))||(@Coordinate(y,0)-@Coordinate(y,-1)) / Version: 1
Note: Evaluates to 0 if feature is loop, and 1, if it is not.
LoopTester: ExpressionEvaluator
    EXPRESSION = (@Coordinate(x,0)-@Coordinate(x,-1))||(@Coordinate(y,0)-@Coordinate(y,-1))
    VAL_ATTR = _isLoop
    -> TESTER
Note: TESTER [Tester:1] / Test Description: <not set> / TEST &_isLoop = 0 / Condition: OR / Composite Test Expression: <not set> / Version: 1
TESTER: Tester
    TEST_MODE = Automatic
    BOOL_OP = OR
    TEST_CLAUSE = TEST &_isLoop = 0
    TEST_LIST = &_isLoop,=,0
    PASSED -> PASSED (output)
    FAILED -> FAILED (output)
PASSED (output)
FAILED (output)
NON-LINEAR (output)

FME custom transformer LoopFilter_5
Tests whether a line is a loop, i.e. whether its end matches the beginning.
The transformers outputs loops through PASSED port, and non-loops through FAILED port.
The isLoop attribute added to each feature. 1 means the feature is loop, and zero means it is not.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> LineFilter
Note: LoopFilter / Dmitri Bagh / July 11, 2005
LineFilter: GeometryFilter
    LINE -> LoopTester
    POINT -> NON-LINEAR (output)
    ARC -> NON-LINEAR (output)
    AREA -> NON-LINEAR (output)
    ELLIPSE -> NON-LINEAR (output)
    TEXT -> NON-LINEAR (output)
    NULL -> NON-LINEAR (output)
Note: LoopTester [ExpressionEvaluator:1] / _isLoop = (@Coordinate(x,0)-@Coordinate(x,-1))||(@Coordinate(y,0)-@Coordinate(y,-1)) / Version: 1
Note: Evaluates to 0 if feature is loop, and 1, if it is not.
LoopTester: ExpressionEvaluator
    EXPRESSION = (@Coordinate(x,0)-@Coordinate(x,-1))||(@Coordinate(y,0)-@Coordinate(y,-1))
    VAL_ATTR = _isLoop
    -> TESTER
Note: TESTER [Tester:1] / Test Description: <not set> / TEST &_isLoop = 0 / Condition: OR / Composite Test Expression: <not set> / Version: 1
TESTER: Tester
    TEST_MODE = Automatic
    BOOL_OP = OR
    TEST_CLAUSE = TEST &_isLoop = 0
    TEST_LIST = &_isLoop,=,0
    PASSED -> PASSED (output)
    FAILED -> FAILED (output)
PASSED (output)
FAILED (output)
NON-LINEAR (output)

FME custom transformer LoopFilter_6
Tests whether a line is a loop, i.e. whether its end matches the beginning.
The transformers outputs loops through PASSED port, and non-loops through FAILED port.
An isLoop attribute is added to each feature. 1 means the feature is loop, and zero means it is not.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> LineFilter
Note: LoopFilter / Dmitri Bagh / July 11, 2005
LineFilter: GeometryFilter
    LINE -> LoopTester
    POINT -> NON-LINEAR (output)
    ARC -> NON-LINEAR (output)
    AREA -> NON-LINEAR (output)
    ELLIPSE -> NON-LINEAR (output)
    TEXT -> NON-LINEAR (output)
    NULL -> NON-LINEAR (output)
Note: LoopTester [ExpressionEvaluator:1] / _isLoop = (@Coordinate(x,0)-@Coordinate(x,-1))||(@Coordinate(y,0)-@Coordinate(y,-1)) / Version: 1
Note: Evaluates to 0 if feature is loop, and 1, if it is not.
LoopTester: ExpressionEvaluator
    EXPRESSION = (@Coordinate(x,0)-@Coordinate(x,-1))||(@Coordinate(y,0)-@Coordinate(y,-1))
    VAL_ATTR = _isLoop
    -> TESTER
Note: TESTER [Tester:1] / Test Description: <not set> / TEST &_isLoop = 0 / Condition: OR / Composite Test Expression: <not set> / Version: 1
TESTER: Tester
    TEST_MODE = Automatic
    BOOL_OP = OR
    TEST_CLAUSE = TEST &_isLoop = 0
    TEST_LIST = &_isLoop,=,0
    PASSED -> PASSED (output)
    FAILED -> FAILED (output)
PASSED (output)
FAILED (output)
NON-LINEAR (output)

FME custom transformer LoopFilter_7
Tests whether a line is a loop, i.e. whether its end matches the beginning.
The transformers outputs loops through PASSED port, and non-loops through FAILED port.
The isLoop attribute added to each feature. 1 means the feature is loop, and zero means it is not.
Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> LineFilter
Note: LoopFilter / Dmitri Bagh / July 11, 2005
LineFilter: GeometryFilter
    LINE -> LoopTester
    POINT -> NON-LINEAR (output)
    ARC -> NON-LINEAR (output)
    AREA -> NON-LINEAR (output)
    ELLIPSE -> NON-LINEAR (output)
    TEXT -> NON-LINEAR (output)
    NULL -> NON-LINEAR (output)
Note: LoopTester [ExpressionEvaluator:1] / _isLoop = (@Coordinate(x,0)-@Coordinate(x,-1))||(@Coordinate(y,0)-@Coordinate(y,-1)) / Version: 1
Note: Evaluates to 0 if feature is loop, and 1, if it is not.
LoopTester: ExpressionEvaluator
    EXPRESSION = (@Coordinate(x,0)-@Coordinate(x,-1))||(@Coordinate(y,0)-@Coordinate(y,-1))
    VAL_ATTR = _isLoop
    -> TESTER
Note: TESTER [Tester:1] / Test Description: <not set> / TEST &_isLoop = 0 / Condition: OR / Composite Test Expression: <not set> / Version: 1
TESTER: Tester
    TEST_MODE = Automatic
    BOOL_OP = OR
    TEST_CLAUSE = TEST &_isLoop = 0
    TEST_LIST = &_isLoop,=,0
    PASSED -> PASSED (output)
    FAILED -> FAILED (output)
PASSED (output)
FAILED (output)
NON-LINEAR (output)

FME custom transformer LoopFilter_8
Tests whether a line is a loop, i.e. whether its end matches the beginning.
The transformers outputs loops through PASSED port, and non-loops through FAILED port.
An isLoop attribute is added to each feature. 1 means the feature is loop, and zero means it is not.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> LineFilter
Note: LoopFilter / Dmitri Bagh / July 11, 2005
LineFilter: GeometryFilter
    LINE -> LoopTester
    POINT -> NON-LINEAR (output)
    ARC -> NON-LINEAR (output)
    AREA -> NON-LINEAR (output)
    ELLIPSE -> NON-LINEAR (output)
    TEXT -> NON-LINEAR (output)
    NULL -> NON-LINEAR (output)
Note: LoopTester [ExpressionEvaluator:1] / _isLoop = (@Coordinate(x,0)-@Coordinate(x,-1))||(@Coordinate(y,0)-@Coordinate(y,-1)) / Version: 1
Note: Evaluates to 0 if feature is loop, and 1, if it is not.
LoopTester: ExpressionEvaluator
    EXPRESSION = (@Coordinate(x,0)-@Coordinate(x,-1))||(@Coordinate(y,0)-@Coordinate(y,-1))
    VAL_ATTR = _isLoop
    -> TESTER
Note: TESTER [Tester:1] / Test Description: <not set> / TEST &_isLoop = 0 / Condition: OR / Composite Test Expression: <not set> / Version: 1
TESTER: Tester
    TEST_MODE = Automatic
    BOOL_OP = OR
    TEST_CLAUSE = TEST &_isLoop = 0
    TEST_LIST = &_isLoop,=,0
    PASSED -> PASSED (output)
    FAILED -> FAILED (output)
PASSED (output)
FAILED (output)
NON-LINEAR (output)

FME custom transformer StaticMapFetcher_2
Fetches a Google Static Map image by performing an HTTP GET operation on the URL specified according to Google Static Maps API and then returning the resulting data as the geometry of a raster feature. The raster feature will be georeferenced in the Spherical Mercator coordinate system. The output feature also has a _static_map_url attribute which contains the url used to fetch the image.
If no latitude and longitude parameters are defined, then they will be taken from the geometry of the incoming feature.
Connect the trasnformer in your workspace and set the following paramters:
- Latitude and Longitude in DD.DDDDD format
- Zoom Level from 0 (entire earth) to 21 (max zoom)
- Image size in pixels
- Map type
- Client ID (optional)
- Crypto Key (optional)
The maximum image width and height provided by google to free users is 640 pixels. If you are using the transformer with a "Google Maps for Business" Client ID and Key, the output image's width and height can be up to 2048 pixels.
This transformer uses the Google Maps API. Please review the restrictions on use at https://developers.google.com/maps/terms.
Copyright (c) 2013 Safe Software Inc.
Permission is granted to anyone, free of charge, to use, modify and distribute the object code form of this transformer for any purpose, subject to the following restrictions:
1) The origin of this transformer and associated FME(R) software must not be misrepresented.
2) This transformer may only be used in conjunction with a validly licensed copy of FME software.
3) Use of the the Google Maps API is subject to Google's Terms of Service. Compliance with the Terms of Service is the responsibility of the end user. 
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- mode = Regular   # Using a Google Maps for Business key
- LATITUDE = 0   # Latitude
- LONGITUDE = 0   # Longitude
- ZOOM = 0   # Zoom Level
- SIZEY = 640   # Image Height
- SIZEX = 640   # Image Width
- maptype = roadmap   # Map Type
- clientid =   # Client ID (Google Maps Business)
- cryptokey =   # Crypto Key (Google Maps Business)

INPUT (input)
    -> AttributeExposer
AttributeExposer
    ATTR_LIST = _zoom,_center_x,_center_y,_rows,_cols
    -> AttributeCreator
Note: Retrieve parameters
AttributeCreator
    NUM_PRIOR_FEATURES = 0
    ATTR_LIST = _zoom,$(ZOOM),_cols,$(SIZEX),_rows,$(SIZEY),_maptype,$(maptype)
    NUM_SUBSEQUENT_FEATURES = 0
    -> GeometryFilter
Note: Detemine if user wants to / use Maps for Business key
Tester
    TEST_MODE = Automatic
    BOOL_OP = OR
    TEST_CLAUSE = TEST $(mode) = Regular
    TEST_DESCRIPTION = ""
    PASSED -> Concatenator
    FAILED -> AttributeCreator_2
Note: Georeferencing the tile requires a few assumptions: / 1) The width and height of the earth in Spherical Mercator was determined / 2) The actual bounds of the tile is inferred from the zoom level.
RASTER (output)
Note: HTTP Call has failed. Check the _http_status_code attribute on the feature
<REJECTED> (output)

Bookmark: Find Center Point
GeometryFilter
    NULL -> Center_X_Setter
    LINE -> BoundingBoxAccumulator_2
    ARC -> BoundingBoxAccumulator_2
    AREA -> BoundingBoxAccumulator_2
    ELLIPSE -> BoundingBoxAccumulator_2
    RASTER -> BoundingBoxAccumulator_2
    COLLECTION -> BoundingBoxAccumulator_2
    POINT -> CoordinateFetcher
Note: Get Coordinates
CoordinateFetcher
    Z_ATTR = _z
    Z_DEFAULT = 0
    Y_ATTR = _center_y
    X_ATTR = _center_x
    IND = 0
    -> AttributeCopier
AttributeCopier
    ATTR_LIST = _center_x_sm,_center_x,_center_y_sm,_center_y,_center_x_ll84,_center_x,_center_y_ll84,_center_y
    -> AttributeReprojector
Note: Reproject the / coordinates
AttributeReprojector
    XATTR = _center_x_sm
    SOURCE = LL84
    DEST = SPHERICAL_MERCATOR
    YATTR = _center_y_sm
    -> Tester

Bookmark: Take the center point of the features' bounding box
BoundingBoxAccumulator_2
    GROUP_BY = _zoom _rows _cols
    BOUNDING_BOX -> BoundsExtractor
BoundsExtractor
    YMIN = _ymin
    YMAX = _ymax
    ZMIN = _zmin
    ZMAX = _zmax
    XMIN = _xmin
    XMAX = _xmax
    -> CenterPointReplacer
CenterPointReplacer
    CENTERPOINT -> CoordinateFetcher

Bookmark: Retrieve input latitude and Longitude as attributes
Center_X_Setter: AttributeSetter
    VAL = $(LONGITUDE)
    DEST_ATTR = _center_x
    -> Center_Y_Setter
Center_Y_Setter: AttributeSetter
    VAL = $(LATITUDE)
    DEST_ATTR = _center_y
    -> AttributeCopier

Bookmark: Prepare to fetch static map without user key
Note: Build URL for request
Concatenator
    PARM_LINE = http://maps.googleapis.com/maps/api/staticmap?center=@Value(_center_y),@Value(_center_x)&zoom=@Value(_zoom)&size=@Value(_cols)x@Value(_rows)&maptype=@Value(_maptype)&sensor=false
    VAL_ATTR = _static_map_url
    -> ImageFetcher_2

Bookmark: Prepare to fetch static map with user key
Note: Get Crypto Key
AttributeCreator_2
    NUM_PRIOR_FEATURES = 0
    ATTR_LIST = cryptokey,$(cryptokey),encodedsignature,""
    NUM_SUBSEQUENT_FEATURES = 0
    -> BuildURLToSign
Note: Build URL part needed for / creating Digital Signature
BuildURLToSign: StringConcatenator
    PARM_LINE = /maps/api/staticmap?center=@Value(_center_y),@Value(_center_x)&zoom=@Value(_zoom)&size=@Value(_cols)x@Value(_rows)&maptype=@Value(_maptype)&client=$(clientid)&sensor=false
    VAL_ATTR = URLtoSign
    -> PythonCaller_2
Note: Create Digital Signature
PythonCaller_2
    PYTHONSOURCE:
      import fmeobjects,base64,hashlib,hmac

      # Template Function interface:
      def processFeature(feature):

          # Get the key value and decode it
          cryptokey = feature.getAttribute('cryptokey')
          decodedKey = base64.urlsafe_b64decode(str(cryptokey))

          # Create Digital Signature for the request - Diffrerent requests need different signatures
          urltosign = feature.getAttribute('URLtoSign')
          signature = hmac.new(decodedKey,urltosign,hashlib.sha1)

          # Encode the Digital Signature and return it as an attribute value
          encodedsign = base64.urlsafe_b64encode(signature.digest())
          feature.setAttribute('encodedsignature',encodedsign)
    PYTHONSYMBOL = processFeature
    -> BuildURL_3
Note: Build Complete / URL for request
BuildURL_3: StringConcatenator
    PARM_LINE = http://maps.googleapis.com@Value(URLtoSign)&signature=@Value(encodedsignature)
    VAL_ATTR = _static_map_url
    -> ImageFetcher_2

Bookmark: Fetch Tile
Note: Get the static image
ImageFetcher_2
    AUTH_METHOD = Basic
    RASTER_TYPE = PNG
    HTTP_PROXY_AUTH_METHOD = Basic
    URL = @Value(_static_map_url)
    RASTER -> Concatenator_2
    <REJECTED> -> AttributeRemover_2
Note: Create basename
Concatenator_2
    PARM_LINE = @Value(_zoom)_@Value(_center_x)_@Value(_center_y)_@Value(_cols)_@Value(_rows)
    VAL_ATTR = fme_basename
    -> StringReplacer
Note: Clean up dots / from name
StringReplacer
    REGEXP = no
    SRC_ATTR = fme_basename
    CASE = no
    FIND_TEXT = .
    RESULT_ATTR = fme_basename
    -> RasterPaletteResolver

Bookmark: Resolve the PNG Palettes
RasterPaletteResolver
    -> PythonCaller_3

Bookmark: Georeference Tile
PythonCaller_3
    PYTHONSOURCE:
      class calc_bounds(object):
      	def __init__(self):
      		pass

      	def google_tile_bounds(self,zoom,rows,cols):

      		X_MAX_WIDTH  = 20037508.3427892
      		Y_MAX_HEIGHT = 20037509.9173396

      		width = (2*X_MAX_WIDTH*cols)/(256*2**(zoom))
      		height = (2*Y_MAX_HEIGHT*rows)/(256*2**(zoom))

      		return (width,height)

      	def input(self,feature):
      		colmns = feature.getRealAttribute("_cols")
      		zoom = feature.getRealAttribute("_zoom")
      		rows = feature.getRealAttribute("_rows")
      		(width,height) = self.google_tile_bounds(zoom,rows,colmns)

      		h_width = width/2.0

      		h_height = height/2.0

      		cp_x = feature.getRealAttribute("_center_x_sm")
      		cp_y = feature.getRealAttribute("_center_y_sm")

      		left = cp_x - h_width
      		right = cp_x + h_width

      		top = cp_y + h_height
      		bottom = cp_y - h_height


      		feature.setAttribute("_top",top)
      		feature.setAttribute("_bottom",bottom)
      		feature.setAttribute("_left",left)
      		feature.setAttribute("_right",right)

      		self.pyoutput(feature)
    PYTHONSYMBOL = calc_bounds
    -> AttributeExposer_2
AttributeExposer_2
    ATTR_LIST = _top,_bottom,_left,_right
    -> RasterGeoreferencer
RasterGeoreferencer
    POINTANDANGLE_OR_EXTENTS = Extents
    X_UL_COORD = @Value(_left)
    Y_UL_COORD = @Value(_top)
    X_UR_COORD = @Value(_right)
    X_LL_COORD = @Value(_left)
    Y_UR_COORD = @Value(_top)
    Y_LL_COORD = @Value(_bottom)
    X_LR_COORD = @Value(_right)
    Y_LR_COORD = @Value(_bottom)
    -> CoordinateSystemSetter
CoordinateSystemSetter
    COORDSYS = SPHERICAL_MERCATOR
    -> AttributeRemover

Bookmark: Cleanup
AttributeRemover
    REMOVE_ATTRS = _zoom,_rows,_cols,_xmax,_xmin,_ymax,_ymin,_zmax,_zmin,_center_x,_center_x_sm,_center_x_ll84,_center_y,_center_y_sm,_center_y_ll84,_maptype,_z,cryptokey,encodedsignature,URLtoSign,_http_status_code,_top,_bottom,_left,_right
    -> RASTER (output)
AttributeRemover_2
    REMOVE_ATTRS = _zoom,_rows,_cols,_xmax,_xmin,_ymax,_ymin,_zmax,_zmin,_center_x,_center_x_sm,_center_x_ll84,_center_y,_center_y_sm,_center_y_ll84,_maptype,_z,cryptokey,encodedsignature,URLtoSign
    -> <REJECTED> (output)

FME custom transformer AzimuthCalculator_2
Calculates the angle and the azimuth of a line or a polyline.
An Azimuth value can range from -180 to 180 With North as zero, South as -180, East as 90 and West as -90. 
Angles increase counterclockwise from the reference point of East (which represents zero degrees).
For polylines it returns the angle and azimuth of a line connecting the first and the last verteices of the polyline. 
The resultant lines have two new attributes - acAngle and acAzimuth.
For getting information about each segment of the polyline use PolylineAnalyzer.
This transformer uses an embedded version of " LoopFilter " custom transformer.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Note: Azimuth Calculator / - Dean Hintz June 13 2005 / - Dmitri Bagh June 30 2005 (minor edits)
LINE (input)
    -> GeometryFilter
Note: Removes all intermediate attributes
ATTRIBUTEREMOVER: AttributeRemover
    REMOVE_ATTRS = _isLoop,acX1,acY1,acZ1,acX2,acY2,acZ2
    -> AZIMUTH (output)
AZIMUTH (output)

Bookmark: Input Filter
  Sorts out all unsuitable features - non linear, and loops.
Note: passes only lines to the next transfomer
GeometryFilter
    BREAK_AGG = No
    LINE -> LoopFilter
    POINT -> Not_Line (output)
    ARC -> Not_Line (output)
    AREA -> Not_Line (output)
    ELLIPSE -> Not_Line (output)
    TEXT -> Not_Line (output)
    RASTER -> Not_Line (output)
    POINTCLOUD -> Not_Line (output)
    SURFACE -> Not_Line (output)
    SOLID -> Not_Line (output)
    COLLECTION -> Not_Line (output)
    NULL -> Not_Line (output)
Note: tests whether a line is a loop
LoopFilter
    PASSED -> LOGGER_2
    FAILED -> COORDINATEFETCHER
LOGGER_2: Logger
    MAXFEATS = 20
    MESSAGE = Feature is a loop
    MAXCOORDS = 3
Not_Line (output)

Bookmark: Angle Calculations
COORDINATEFETCHER: CoordinateFetcher
    Z_ATTR = acZ1
    Z_DEFAULT = -9999
    Y_ATTR = acY1
    X_ATTR = acX1
    IND = 0
    -> COORDINATEFETCHER_2
COORDINATEFETCHER_2: CoordinateFetcher
    Z_ATTR = acZ2
    Z_DEFAULT = -9999
    Y_ATTR = acY2
    X_ATTR = acX2
    IND = -1
    -> EXPRESSIONEVALUATOR_2
Note: EXPRESSIONEVALUATOR_2 [ExpressionEvaluator:1] / acAngle = acos((&acX2-&acX1)/sqrt(pow((&acY2-&acY1),2) + pow((&acX2-&acX1),2)))* (180/3.141592653589... / Version: 1
EXPRESSIONEVALUATOR_2: ExpressionEvaluator
    EXPRESSION = acos((&acX2-&acX1)/sqrt(pow((&acY2-&acY1),2) + pow((&acX2-&acX1),2)))* (180/3.1415926535897932)
    VAL_ATTR = acAngle
    -> EXPRESSIONEVALUATOR_6
EXPRESSIONEVALUATOR_6: ExpressionEvaluator
    EXPRESSION = ((&acY2-&acY1)<0)?(360-&acAngle):(&acAngle)
    VAL_ATTR = acAngle
    -> TESTER

Bookmark: Azimuth Calculations
  Testers check quadrand, and calculate the Azimuth Accordingly
TESTER: Tester
    TEST_MODE = Automatic
    BOOL_OP = OR
    TEST_CLAUSE = TEST &acAngle > 90
    TEST_LIST = &acAngle,>,90
    PASSED -> TESTER_2
    FAILED -> EXPRESSIONEVALUATOR_3
TESTER_2: Tester
    TEST_MODE = Automatic
    BOOL_OP = OR
    TEST_CLAUSE = TEST &acAngle ">" 270
    TEST_LIST = &acAngle,""">""",270
    FAILED -> EXPRESSIONEVALUATOR_3
    PASSED -> EXPRESSIONEVALUATOR_5
EXPRESSIONEVALUATOR_5: ExpressionEvaluator
    EXPRESSION = 450 - &acAngle
    VAL_ATTR = acAzimuth
    -> ATTRIBUTEREMOVER
EXPRESSIONEVALUATOR_3: ExpressionEvaluator
    EXPRESSION = 90 - &acAngle
    VAL_ATTR = acAzimuth
    -> ATTRIBUTEREMOVER

FME custom transformer UnconditionalFeatureMerger_2
This transformer merges sets of attributes onto all REQUESTOR features. Essentially it is an unconditional merge of feature attributes.
The user can choose between two modes: One Supplier, or All Suppliers.
In One Supplier mode, All REQUESTORS will receive a copy of the attributes of the first SUPPLIER feature, and emerge from the COMPLETE output port. The first SUPPLIER emerges from the REFERENCED output port; any others through the UNREFERENCED port.
In All Suppliers mode, All REQUESTORS will receive a copy of the attributes of all SUPPLIER features, and emerge from the COMPLETE output port. All SUPPLIER features emerge from the REFERENCED output port.
Copyright (c) 2012 Safe Software Inc. 
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- OneForAllOrAllForOne = One   # Supplier Selection

REQUESTOR (input)
    -> AttributeCreator_2
SUPPLIER (input)
    -> Sampler
COMPLETE (output)
REFERENCED (output)

Bookmark: Create Common Join
AttributeCreator_2
    ATTR_LIST = _FeatureMergeJoinAttr,1
    -> FeatureMerger [input 1]
AttributeCreator
    ATTR_LIST = _FeatureMergeJoinAttr,1
    -> FeatureMerger [input 2]

Bookmark: Drop Excess Suppliers
Sampler
    SAMPLE_TYPE_LONG = First N Features
    RATE = 1
    SAMPLED -> AttributeCreator
    NOT_SAMPLED -> Tester
Tester
    TEST_MODE = Automatic
    BOOL_OP = OR
    TEST_CLAUSE = TEST "$(OneForAllOrAllForOne)" = "All"
    TEST_DESCRIPTION = ""
    PASSED -> AttributeCreator
    FAILED -> UNREFERENCED (output)
UNREFERENCED (output)

Bookmark: Merge Attributes
FeatureMerger
    REFERATTR = _FeatureMergeJoinAttr
    PROCESS_DUPS = Yes
    REFEEATTR = _FeatureMergeJoinAttr
    MERGE_TYPE = Attributes Only
    BUILD_INCOMPLETE = No
    REFERENCED -> AttributeExpressionRemover
    COMPLETE -> AttributeExpressionRemover_2

Bookmark: Clean Up Output
AttributeExpressionRemover_2
    ATTR_EXP = _FeatureMerge*
    -> COMPLETE (output)
AttributeExpressionRemover
    ATTR_EXP = _FeatureMerge*
    -> REFERENCED (output)

FME custom transformer LoopFilter
Tests whether a line is a loop, i.e. whether its end matches the beginning.
The transformers outputs loops through PASSED port, and non-loops through FAILED port.
An isLoop attribute is added to each feature. 1 means the feature is loop, and zero means it is not.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> LineFilter
Note: LoopFilter / Dmitri Bagh / July 11, 2005
LineFilter: GeometryFilter
    LINE -> LoopTester
    POINT -> NON-LINEAR (output)
    ARC -> NON-LINEAR (output)
    AREA -> NON-LINEAR (output)
    ELLIPSE -> NON-LINEAR (output)
    TEXT -> NON-LINEAR (output)
    NULL -> NON-LINEAR (output)
Note: LoopTester [ExpressionEvaluator:1] / _isLoop = (@Coordinate(x,0)-@Coordinate(x,-1))||(@Coordinate(y,0)-@Coordinate(y,-1)) / Version: 1
Note: Evaluates to 0 if feature is loop, and 1, if it is not.
LoopTester: ExpressionEvaluator
    EXPRESSION = (@Coordinate(x,0)-@Coordinate(x,-1))||(@Coordinate(y,0)-@Coordinate(y,-1))
    VAL_ATTR = _isLoop
    -> TESTER
Note: TESTER [Tester:1] / Test Description: <not set> / TEST &_isLoop = 0 / Condition: OR / Composite Test Expression: <not set> / Version: 1
TESTER: Tester
    TEST_MODE = Automatic
    BOOL_OP = OR
    TEST_CLAUSE = TEST &_isLoop = 0
    TEST_LIST = &_isLoop,=,0
    PASSED -> PASSED (output)
    FAILED -> FAILED (output)
PASSED (output)
FAILED (output)
NON-LINEAR (output)
