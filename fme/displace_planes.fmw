FME workspace displace_planes.fmw
Shutdown Python:
      import os, shutil, fmeobjects

      source = FME_MacroValues['SourceDataset_FFS']
      dest = FME_MacroValues['DestDataset_FFS']

      source = source.replace("\\","/")
      dest = dest.replace("\\","/")

      if os.path.isfile(dest):
          os.remove(source)
          shutil.move(dest, source)

Parameters:
- SourceDataset_FFS = $(FME_SHAREDRESOURCE_TEMP)/planez.ffs   # Source FME Feature Store (FFS) File(s)
- DestDataset_FFS = $(FME_SHAREDRESOURCE_TEMP)/planez_temp.ffs   # Destination FME Feature Store (FFS) File

Readers:
- FFS_1: FFS from $(SourceDataset_FFS)

Writers:
- FFS_2: FFS to $(DestDataset_FFS)

Planes (reader FFS_1)
    -> AttributeExposer
AttributeExposer
    ATTR_LIST = speed,heading,flight_id,altitude,aircraft_model,_iterations
    -> Logger
Logger
    MESSAGE = Feature is:
    MAXFEATS = 1
    MAXCOORDS = 1
    LOGGED -> Tester
Tester
    TEST_MODE = Automatic
    TEST_DESCRIPTION = ""
    BOOL_OP = OR
    TEST_CLAUSE = TEST @Value(_iterations) > 60
    PASSED -> Sampler
    FAILED -> AttributeCreator
Sampler
    RATE = 1
    SAMPLE_TYPE_LONG = First N Features
    SAMPLED -> FMEServerJobSubmitter
FMEServerJobSubmitter
    PASSWORD =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
    USERNAME = fmepediademos
    SERVER_NAME = http://fmepedia2014-safe-software.fmecloud.com
    WORKSPACE_NAME = plane_generator.fmw
    BLOCKING = No
    REPOSITORY = spatialdashboard
    SERVER_PORT = 0
    WORKSPACE_PARAMETERS = min_y,615000,max_y,660000,min_x,1790000,max_x,1900000,num_planes,30,DestDataset_FFS,$(SourceDataset_FFS)
    SUBSECTION = SERVER_JOB_SUBMITTER
    PRIORITY = 100
AttributeCreator
    ATTR_LIST = _iterations,@int(@Value(_iterations) + 1)
    -> Offsetter
Offsetter
    YOFF = @double(@Value(speed))*5/3.6  * @cos(@Value(heading))
    ZOFF = 0
    XOFF = @double(@Value(speed))*5/3.6  * @sin(@Value(heading))
    OFFSET -> Reprojector
    OFFSET -> Planes (writer FFS_2)
Reprojector
    DEST = LL83
    RASTER_CELL_SIZE = Preserve Cells
    STROKE_ARCS = Yes
    SOURCE = CA83-III
    INTERPOLATION_TYPE_NAME = Nearest Neighbor
    REPROJECTED -> CoordinateExtractor
CoordinateExtractor
    Y_ATTR = y_coord
    X_ATTR = x_coord
    Z_DEFAULT = -9999
    Z_ATTR = _z
    IND = 0
    -> JSONConcatenator
JSONConcatenator: StringConcatenator
    PARM_LINE:
      {
          ws_op : "send",
          ws_msg : "{ 'flight_id' : '@Value(flight_id)', 'latitude' : '@Value(y_coord)', 'longitude' : '@Value(x_coord)', 'heading' : '@Value(heading)','speed':'@Value(speed)','altitude':'@Value(altitude)', 'aircraft_model' : '@Value(aircraft_model)' }"
      }
    VAL_ATTR = notify_content
    -> Decelerator
Decelerator
    DECEL_TYPE = Per Feature Delay
    DELAY = 0.05
    -> WebSocketSender
WebSocketSender
    PREAMBLE:
      {
          ws_op : "open",
          ws_stream_id : "plane_in"
      }
    DATA = @Value(notify_content)
    HOST = wss://localhost:7078/websocket
Planes (writer FFS_2)
