FME workspace sf_bus_reader.fmw

Parameters:
- SourceDataset_XML = http://webservices.nextbus.com/service/publicXMLFeed?command=vehicleLocations&a=sf-muni&r=N&t=0   # Source XML File(s)

Readers:
- XML_1: XML from $(SourceDataset_XML)

vehicle (reader XML_1)
    attributes: vehicle.dirTag xml_char(7), vehicle.heading xml_decimal(4,0), vehicle.id xml_decimal(5,0), vehicle.lat xml_decimal(10,7), vehicle.leadingVehicleId xml_decimal(5,0), vehicle.lon xml_decimal(10,5), vehicle.predictable xml_char(6), vehicle.routeTag xml_char(2), vehicle.secsSinceReport xml_decimal(3,0), vehicle.speedKmHr xml_decimal(18,15), xml_fragment xml_xml, xml_id xml_char(16), xml_matched_element xml_char(8)
    -> StringConcatenator_2
StringConcatenator_2
    PARM_LINE:
      {
          ws_op : 'send',
          ws_msg : "{ 'bus_id': '@Value(vehicle.id)', 'latitude': '@Value(vehicle.lat)', 'longitude': '@Value(vehicle.lon)', 'speed': '@Value(vehicle.speedKmHr)'}"
      }
    VAL_ATTR = notify_content
    -> WebSocketSender_2
WebSocketSender_2
    PREAMBLE:
      {
          ws_op : 'open',
          ws_stream_id : 'bus_in'
      }
    DATA = @Value(notify_content)
    HOST = wss://localhost:7078/websocket
