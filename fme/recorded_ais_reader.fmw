FME workspace recorded_ais_reader.fmw

Parameters:
- prev_path =   # Previous file path for deletion
- SourceDataset_TEXTLINE = C:\Users\dvanniekerk\Documents\My FME Server Workspaces\2012-07-02_SanFran_AIS_recording.txt   # Source Text File(s)
- token = e21c4f31773c1a7e170d85daa5d4ad14f35ca485   # FME Server REST token

Readers:
- TEXTLINE_1: TEXTLINE from $(SourceDataset_TEXTLINE)

text_line (reader TEXTLINE_1)
    attributes: text_line_data buffer
    -> Tester_2
Tester_2
    TEST_MODE = Automatic
    TEST_DESCRIPTION = ""
    BOOL_OP = OR
    TEST_CLAUSE = TEST "text_line_data" NOT_ATTRIBUTE_IS_EMPTY "<Unused>"
    PASSED -> AttributeRenamer
AttributeRenamer
    ATTR_LIST = text_line_data,message,""
    -> Decelerator
Decelerator
    FEATURES_PER_SECOND = 200
    DECEL_TYPE = Limit Features Per Second
    -> UUIDGenerator
FeatureReader
    ATTRIBUTES =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
    FEATURETYPES = ais_addressed_safety_related_message ais_aid_to_navigation_report ais_area_notice ais_assignment_mode_command ais_base_station_report ais_berthing_data ais_binary_acknowledge ais_binary_message_unknown ais_channel_management ais_clearance_time_to_enter_port ais_dangerous_cargo_indication ais_data_link_management_message ais_dgnss_broadcast_binary_message ais_environmental_report ais_extended_class_b_cs_position_report ais_extended_ship_static_voyage_imo236 ais_extended_ship_static_voyage_imo289 ais_fairway_closed ais_group_channel_command ais_interrogation ais_long_range_Broadcast_message ais_marine_traffic_signal ais_meteorological_hydrological_data ais_multiple_slot_binary_message ais_number_persons_on_board ais_position_report ais_route_information ais_safety_related_broadcast_message ais_sar_aircraft_position_report ais_ship_static_and_voyage_related_data ais_single_slot_binary_message ais_standard_class_b_cs_position_report ais_static_data_report ais_synthetic_target ais_text_description ais_tidal_window ais_utc_date_inquiry ais_weather_observation_from_ship_non_wmo ais_weather_observation_from_ship_wmo
    SUPPORTED_SPATIAL_INTERACTIONS = ENVELOPE_INTERSECT%INTERSECTS%CONTAINS%CROSSES%DISJOINT%EQUALS%OVERLAPS%TOUCHES%WITHIN
    DATASET = @Value(file_path)
    COMBINE_GEOM = Result Geometry Only
    COMBINE_ATTRS = Result Attributes Only
    FORMAT = AIS
    ais_route_information -> Logger_27
    ais_single_slot_binary_message -> Logger_31
    ais_standard_class_b_cs_position_report -> Logger_32
    ais_static_data_report -> Logger_33
    ais_synthetic_target -> Logger_34
    ais_text_description -> Logger_35
    ais_tidal_window -> Logger_36
    ais_utc_date_inquiry -> Logger_37
    ais_weather_observation_from_ship_non_wmo -> Logger_38
    ais_weather_observation_from_ship_wmo -> Logger_39
    <OTHER> -> Logger_40
    ais_addressed_safety_related_message -> Logger
    ais_aid_to_navigation_report -> Logger_2
    ais_area_notice -> Logger_3
    ais_assignment_mode_command -> Logger_4
    ais_base_station_report -> Logger_5
    ais_berthing_data -> Logger_6
    ais_binary_acknowledge -> Logger_7
    ais_binary_message_unknown -> Logger_8
    ais_channel_management -> Logger_9
    ais_clearance_time_to_enter_port -> Logger_10
    ais_dangerous_cargo_indication -> Logger_11
    ais_data_link_management_message -> Logger_12
    ais_dgnss_broadcast_binary_message -> Logger_13
    ais_environmental_report -> Logger_14
    ais_extended_class_b_cs_position_report -> Logger_15
    ais_extended_ship_static_voyage_imo236 -> Logger_16
    ais_extended_ship_static_voyage_imo289 -> Logger_17
    ais_fairway_closed -> Logger_18
    ais_group_channel_command -> Logger_19
    ais_interrogation -> Logger_20
    ais_long_range_Broadcast_message -> Logger_21
    ais_marine_traffic_signal -> Logger_22
    ais_meteorological_hydrological_data -> Logger_23
    ais_multiple_slot_binary_message -> Logger_24
    ais_number_persons_on_board -> Logger_25
    ais_safety_related_broadcast_message -> Logger_28
    ais_sar_aircraft_position_report -> Logger_29
    ais_ship_static_and_voyage_related_data -> Logger_30
    ais_position_report -> CoordinateExtractor
    INITIATOR -> VariableRetriever_2
Logger [off]
    MESSAGE = Feature is:
    MAXFEATS = 20
    MAXCOORDS = 20
Logger_2 [off]
    MESSAGE = Feature is:
    MAXFEATS = 20
    MAXCOORDS = 20
Logger_3 [off]
    MESSAGE = Feature is:
    MAXFEATS = 20
    MAXCOORDS = 20
WebSocketSender
    PREAMBLE:
      {
          "ws_op" : "open",
          "ws_stream_id" : "ship_in"
      }
    DATA = @Value(notify_content)
    HOST = ws://localhost:7078/websocket
    -> AttributeRemover
Logger_4 [off]
    MESSAGE = Feature is:
    MAXFEATS = 20
    MAXCOORDS = 20
Logger_5 [off]
    MESSAGE = Feature is:
    MAXFEATS = 20
    MAXCOORDS = 20
Logger_6 [off]
    MESSAGE = Feature is:
    MAXFEATS = 20
    MAXCOORDS = 20
Logger_7 [off]
    MESSAGE = Feature is:
    MAXFEATS = 20
    MAXCOORDS = 20
Logger_8 [off]
    MESSAGE = Feature is:
    MAXFEATS = 20
    MAXCOORDS = 20
Logger_9 [off]
    MESSAGE = Feature is:
    MAXFEATS = 20
    MAXCOORDS = 20
Logger_10 [off]
    MESSAGE = Feature is:
    MAXFEATS = 20
    MAXCOORDS = 20
Logger_11 [off]
    MESSAGE = Feature is:
    MAXFEATS = 20
    MAXCOORDS = 20
Logger_12 [off]
    MESSAGE = Feature is:
    MAXFEATS = 20
    MAXCOORDS = 20
Logger_13 [off]
    MESSAGE = Feature is:
    MAXFEATS = 20
    MAXCOORDS = 20
Logger_14 [off]
    MESSAGE = Feature is:
    MAXFEATS = 20
    MAXCOORDS = 20
Logger_15 [off]
    MESSAGE = Feature is:
    MAXFEATS = 20
    MAXCOORDS = 20
Logger_16 [off]
    MESSAGE = Feature is:
    MAXFEATS = 20
    MAXCOORDS = 20
Logger_17 [off]
    MESSAGE = Feature is:
    MAXFEATS = 20
    MAXCOORDS = 20
Logger_18 [off]
    MESSAGE = Feature is:
    MAXFEATS = 20
    MAXCOORDS = 20
Logger_19 [off]
    MESSAGE = Feature is:
    MAXFEATS = 20
    MAXCOORDS = 20
Logger_20 [off]
    MESSAGE = Feature is:
    MAXFEATS = 20
    MAXCOORDS = 20
Logger_21 [off]
    MESSAGE = Feature is:
    MAXFEATS = 20
    MAXCOORDS = 20
Logger_22 [off]
    MESSAGE = Feature is:
    MAXFEATS = 20
    MAXCOORDS = 20
Logger_23 [off]
    MESSAGE = Feature is:
    MAXFEATS = 20
    MAXCOORDS = 20
Logger_24 [off]
    MESSAGE = Feature is:
    MAXFEATS = 20
    MAXCOORDS = 20
Logger_25 [off]
    MESSAGE = Feature is:
    MAXFEATS = 20
    MAXCOORDS = 20
Logger_27 [off]
    MESSAGE = Feature is:
    MAXFEATS = 20
    MAXCOORDS = 20
Logger_28 [off]
    MESSAGE = Feature is:
    MAXFEATS = 20
    MAXCOORDS = 20
Logger_29 [off]
    MESSAGE = Feature is:
    MAXFEATS = 20
    MAXCOORDS = 20
Logger_30 [off]
    MESSAGE = Feature is:
    MAXFEATS = 20
    MAXCOORDS = 20
Logger_31 [off]
    MESSAGE = Feature is:
    MAXFEATS = 20
    MAXCOORDS = 20
Logger_32 [off]
    MESSAGE = Feature is:
    MAXFEATS = 20
    MAXCOORDS = 20
Logger_33 [off]
    MESSAGE = Feature is:
    MAXFEATS = 20
    MAXCOORDS = 20
Logger_34 [off]
    MESSAGE = Feature is:
    MAXFEATS = 20
    MAXCOORDS = 20
Logger_35 [off]
    MESSAGE = Feature is:
    MAXFEATS = 20
    MAXCOORDS = 20
Logger_36 [off]
    MESSAGE = Feature is:
    MAXFEATS = 20
    MAXCOORDS = 20
Logger_37 [off]
    MESSAGE = Feature is:
    MAXFEATS = 20
    MAXCOORDS = 20
Logger_38 [off]
    MESSAGE = Feature is:
    MAXFEATS = 20
    MAXCOORDS = 20
Logger_39 [off]
    MESSAGE = Feature is:
    MAXFEATS = 20
    MAXCOORDS = 20
Logger_40 [off]
    MESSAGE = Feature is:
    MAXFEATS = 20
    MAXCOORDS = 20

Bookmark: Write out each AIS message
UUIDGenerator
    UUID_ATTR = _uuid
    -> AttributeCreator
AttributeCreator
    ATTR_LIST = filename,ais_@Value(_uuid).txt,shared_resource,$(FME_MOUNTPOINT_TEMP)
    -> AttributeCreator_2
AttributeCreator_2
    ATTR_LIST = file_path,@Value(shared_resource)/@Value(filename)
    -> AttributeFileWriter
AttributeFileWriter
    CHAR_ENCODING = fme-system
    FILE_NAME = @Value(file_path)
    SOURCE_ATTR = message
    -> FeatureReader

Bookmark: Create location message with ship details
CoordinateExtractor
    Y_ATTR = _y
    X_ATTR = _x
    Z_DEFAULT = -9999
    Z_ATTR = _z
    IND = 0
    -> SQLExecutor
Note: Get ship details
SQLExecutor
    SQL_STATEMENT = SELECT * FROM ship_details WHERE  mmsi_number = "@Value(ais_data_mmsi)"
    EXPOSED_ATTRIBUTE_LIST = call_sign,class_general,class_special,mmsi_number,ship_length,tonnage,vessel_name,class_general_desc,class_individual_desc
    DATASET = C:\Users\dvanniekerk\Documents\My FME Server Workspaces\ships.db
    COMBINE_GEOM = Initiator Geometry Only
    COMBINE_ATTRS = Keep Result Attributes if Conflict
    FORMAT = SQLITE3
    RESULT -> StringConcatenator_3
StringConcatenator_3
    PARM_LINE:
      {
          ws_op : "send",
          ws_msg : '{"mmsi_number": "@Value(ais_data_mmsi)",	"heading": "@Value(ais_data_true_heading)","latitude": "@Value(_y)","longitude": "@Value(_x)","call_sign": "@Value(call_sign)","class_general": "@Value(class_general)","class_special": "@Value(class_special)","ship_length": "@Value(ship_length)","tonnage": "@Value(tonnage)","vessel_name": "@Value(vessel_name)",	"class_general_desc": "@Value(class_general_desc)",	"class_special_desc": "@Value(class_individual_desc)"}'
      }
    VAL_ATTR = notify_content
    -> WebSocketSender

Bookmark: Submit the next AIS job
AttributeRemover
    REMOVE_ATTRS = ais_data_mmsi,ais_data_course_over_ground,ais_data_rate_of_turn,ais_data_repeat_indicator,ais_header_message_id,ais_data_radio_status,ais_data_message_type,ais_header_channel,ais_header_prefix,ais_header_message_type,ais_data_navigation_status,ais_data_true_heading,ais_data_position_accuracy,ais_data_time_stamp,ais_data_speed_over_ground,ais_data_raim_flag,ais_data_maneuver_indicator,_x,_y,_z,call_sign,class_general,class_special,mmsi_number,ship_length,tonnage,vessel_name,class_general_desc,class_individual_desc,notify_content
    -> GeometryRemover
GeometryRemover
    -> Aggregator
Aggregator
    SEP = ,
    CONTAIN_INDIVID_GEOMS = No
    ACCUM_ATTRS_NAME = No
    ORDERED = No
    AGGREGATE -> VariableRetriever
VariableRetriever
    SCOPE = Global
    VARNAME = filename_del
    VALUE_ATTR = filename_del
    -> FMEServerJobSubmitter
FMEServerJobSubmitter
    PASSWORD =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
    USERNAME = fmepediademos
    SERVER_NAME = http://localhost
    WORKSPACE_NAME = recorded_ais_reader.fmw
    BLOCKING = No
    REPOSITORY = spatialdashboard
    SERVER_PORT = 0
    WORKSPACE_PARAMETERS = prev_path,@Value(filename_del)
    SUBSECTION = SERVER_JOB_SUBMITTER
    PRIORITY = 1
    SUCCEEDED -> Logger_26
Logger_26
    MESSAGE = Feature is:
    MAXFEATS = 20
    MAXCOORDS = 20

Bookmark: Delete the previous file
VariableRetriever_2
    SCOPE = Global
    VARNAME = filename_del
    VALUE_ATTR = filename_del
    -> Tester
Tester
    TEST_MODE = Automatic
    TEST_DESCRIPTION = ""
    BOOL_OP = OR
    TEST_CLAUSE = TEST "filename_del" NOT_ATTRIBUTE_IS_EMPTY ""
    PASSED -> HTTPDeleter
    FAILED -> VariableSetter
HTTPDeleter
    TARGET_URL = http://localhost/fmerest/v2/resources/FME_MOUNTPOINT_TEMP/filesys/@Value(filename_del)?detail=low&token=$(token)
    STATUS_CODE_ATTR = _http_status_code
    PROXY_AUTH_METHOD = Basic
    FOLLOW_REDIRECTS = Yes
    RESPONSE_HEADER_LIST_ATTR = _headers
    ERROR_ATTR = _error
    USE_COOKIES = No
    VERIFY_SSL_CERTIFICATES = Yes
    AUTH_METHOD = Basic
    TARGET_ATTR = _url_contents
    -> VariableSetter
VariableSetter
    SCOPE = Global
    VALUE = @Value(filename)
    VARNAME = filename_del
