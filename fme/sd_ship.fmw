FME workspace sd_ship.fmw

Parameters:
- SourceDataset_TEXTLINE = $(FME_SHAREDRESOURCE_DATA)/Demos/2012-07-02_SanFran_AIS_recording.txt   # gui_Source Text File(s):_4929
- FME_SHAREDRESOURCE_TEMP = C:/Temp   # Temp location

Readers:
- TEXTLINE_1: TEXTLINE from $(SourceDataset_TEXTLINE)

text_line (reader TEXTLINE_1)
    attributes: text_line_data buffer
    -> Tester
Tester
    TEST_MODE = Automatic
    TEST_CLAUSE = TEST text_line_data NOT_ATTRIBUTE_IS_MISSING ""
    TEST_DESCRIPTION = ""
    BOOL_OP = OR
    PASSED -> AttributeRenamer
AttributeRenamer
    ATTR_LIST = text_line_data,message,
    -> Decelerator
Decelerator
    FEATURES_PER_SECOND = 10
    DECEL_TYPE = Limit Features Per Second
    -> UUIDGenerator
Note: sd_ship.fmw / This job simulates reading from a live AIS feed. It will clean up the temporary files it writes to disk.
FeatureReader
    AIS_CLIP_TO_ENVELOPE = NO
    ATTR_ACCUM_MODE = Only Use Result
    AIS_USE_SEARCH_ENVELOPE = NO
    FORMAT = AIS
    FEATURETYPES_RADIO = FEATURETYPES
    DATASET = @Value(file_path)
    COMBINE_GEOM = Use Result
    INTERACT = <No Spatial Filter>
    FEATURETYPES = ais_position_report
    ATTRIBUTES =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
    ais_position_report -> CoordinateExtractor
CoordinateExtractor
    IND = 0
    Z_ATTR = _z
    Y_ATTR = _y
    X_ATTR = _x
    Z_DEFAULT = -9999
    -> Joiner
Joiner
    ADDED_FIELDS = call_sign class_general class_general_desc class_individual_desc class_special mmsi_number tonnage vessel_name
    FORMAT = SQLITE3
    TABLE = ship_details
    PREFETCH_QUERY:
      SELECT *
      FROM ship_details
    DATASET = $(FME_MF_DIR_ENCODED)data\ships.db
    PREFETCH_EXHAUSTIVE = Yes
    MATCH_MULTIPLE_DISPLAY = Create a feature for each match
    CACHE_SIZE = 5000
    JOIN_KEYS = ais_data_mmsi mmsi_number
    MATCH_RULE_DISPLAY = Match All (1:M)
    JOINED -> JSONTemplater
JSONTemplater
    ROOT_QUERY_EXPR:
      {
          "mmsi_number": fme:get-attribute("mmsi_number"),
          "heading": fme:get-attribute("ais_data_true_heading"),
          "latitude": fme:get-attribute("_y"),
          "longitude": fme:get-attribute("_x"),
          "call_sign": fme:get-attribute("call_sign"),
          "class_general": fme:get-attribute("class_general"),
          "class_special": fme:get-attribute("class_special"),
          "tonnage": fme:get-attribute("tonnage"),
          "vessel_name": fme:get-attribute("vessel_name"),
          "class_general_desc": fme:get-attribute("class_general_desc"),
          "class_special_desc": fme:get-attribute("class_individual_desc")
      }
    VISIBLE_QUERY_VALIDATE = Yes
    RESULT_ATTRIBUTE = ws_msg
    -> WebSocketSender
WebSocketSender
    PREAMBLE:
      {
          ws_op: "open",
          ws_stream_id: "sd_ship"
      }
    DATA:
      {
          ws_op: 'send',
          ws_msg: '@Value(ws_msg)'
      }
    VERIFY_SSL_CERTIFICATES = Yes
    HOST = wss://localhost:7078/websocket
    -> AttributeExposer
AttributeExposer [off]
    ATTR_LIST = fme_dataset
    -> Aggregator [off]
Aggregator [off]
    ACCUM_ATTRS_NAME = No
    ORDERED = Yes
    MODE = Geometry - Assemble One Level
    GROUP_BY = fme_dataset
    AGGREGATE_TYPE = Homogeneous Collection (If Possible)
    SEP = ,
    AGGREGATE -> FileDeleter [off]
FileDeleter: PythonCaller [off]
    PYTHONSYMBOL = processFeature
    PYTHONSOURCE:
      import fme
      import fmeobjects
      import os
      # Template Function interface:
      def processFeature(feature):
          try:
              os.remove(feature.getAttribute('fme_dataset'))
              print "PYTHON DELETE: " + feature.getAttribute('fme_dataset')
          except OSError as e:
              print e.strerror

Bookmark: Write file to disk
UUIDGenerator
    UUID_ATTR = _uuid
    -> AttributeCreator
AttributeCreator
    ATTR_LIST = templocation,$(FME_SHAREDRESOURCE_TEMP)/spatialdashboard
    -> AttributeCreator_2
AttributeCreator_2
    ATTR_LIST = file_path,@Value(templocation)/tempship.txt
    -> AttributeFileWriter
AttributeFileWriter
    FILE_NAME = @Value(file_path)
    OVERWRITE_FILE = Overwrite file
    SOURCE_ATTR = message
    CHAR_ENCODING = fme-system
    -> FeatureReader
