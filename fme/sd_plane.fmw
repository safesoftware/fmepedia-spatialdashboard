FME workspace sd_plane.fmw

Parameters:
- PLANE_RECORDING = $(FME_SHAREDRESOURCE_DATA)/Demos/planes.ffs   # Recorded plane tracking file

Note: sd_plane.fmw / This workspace simulates polling a service for plane information. Typically, these services will require a paid account to access their API.
JSONFragmenter
    JSON_ATTR = _url_contents
    JSON_QUERY = json[*]
    EXPLODE_FORMAT = JSON
    EXTRACT_ATTR = No
    EXPLODED -> Tester
Tester
    TEST_MODE = Automatic
    TEST_CLAUSE = TEST @Value(json_type) = array
    TEST_DESCRIPTION = ""
    BOOL_OP = AND
    PASSED -> JSONExtractor
JSONExtractor
    JSON_ATTR = _url_contents
    EXTRACT_QUERY_TABLE = y_coord json[1] x_coord json[2] flight_id json[13] aircraft_model json[8] heading json[3] speed json[5] altitude json[4]
    EVALUATED -> JSONTemplater
Note: JSONTemplater [JSONTemplater] / Group By: <not set> / Results Attribute: "ws_msg"
JSONTemplater
    ROOT_QUERY_EXPR:
      {
          'id': fme:get-attribute("json_index"),
          'flight_id': fme:get-attribute("flight_id"),
          'latitude': fme:get-attribute("y_coord"),
          'longitude': fme:get-attribute("x_coord"),
          'heading': fme:get-attribute("heading"),
          'speed': fme:get-attribute("speed"),
          'altitude': fme:get-attribute("altitude"),
          'aircraft_model': fme:get-attribute("aircraft_model")
      }
    VISIBLE_QUERY_VALIDATE = Yes
    RESULT_ATTRIBUTE = ws_msg
    -> WebSocketSender
WebSocketSender
    PREAMBLE:
      {
          ws_op : "open",
          ws_stream_id : "sd_plane"
      }
    HOST = wss://localhost:7078/websocket
    VERIFY_SSL_CERTIFICATES = No
    DATA:
      {
          ws_op: 'send',
          ws_msg: '@Value(ws_msg)'
      }
    -> Logger
Logger
    MAXFEATS = 20
    MESSAGE = Feature is:
    MAXCOORDS = 20

Bookmark: Simulates streaming data
Player
    MODE = PLAYBACK
    RECFILE = $(PLANE_RECORDING)
    PLAYED_BACK -> AttributeExposer
AttributeExposer
    ATTR_LIST = _url_contents
    -> Decelerator
Decelerator
    DECEL_TYPE = Per Feature Delay
    DELAY = 5
    -> JSONFragmenter
